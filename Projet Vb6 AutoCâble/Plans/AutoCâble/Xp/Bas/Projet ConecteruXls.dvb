Attribute VB_Name = "FonctionsGlobales"

Function DecalInsertPointLigneTableau_fils_Bas(Y, Ofset)
    DecalInsertPointLigneTableau_fils_Bas = Y - Ofset
End Function
Function DecalInsertPointLigneTableau_fils_Gauche(X, Ofset)
    DecalInsertPointLigneTableau_fils_Gauche = X + Ofset
End Function
Public Function funAttributesLigne_Tableau_fils(MyName As String, Attributes, Tableau, Nb, Optional RangeTitre As Recordset, Optional BoolTirte As Boolean, Optional MyColection As Collection, Optional vignette As Boolean, Optional EPISSURE As Boolean)
Dim Designation As String
Dim MyNb As Long
Dim MyNbStart As Long
Dim msgAttib As String
If vignette = True Then
    If EPISSURE = False Then
        Designation = ".HAUT"
        MyNb = 4
        MyNbStart = 2
    Else
        MyNbStart = 3
         Designation = ""
      MyNb = 3
    End If
Else
    Designation = ""
      MyNb = Nb
      If BoolTirte = True Then
        MyNbStart = 2
      Else
      MyNbStart = 0
      End If
End If
On erro GoTo MsgError
For i = MyNbStart To MyNb
DoEvents
    If BoolTirte = False Then
        Attributes(i).TextString = "" & Tableau(i)
    Else
        msgAttib = Tableau(i)
       If EPISSURE = False Then
            Attributes(MyColection.Item(Replace(RangeTitre.Fields(i).Name, "PRECO", "PRECO.") & Designation)).TextString = Trim("" & Tableau(i))
        Else
            Attributes(MyColection.Item("EPISSURE")).TextString = Trim("" & Tableau(i))

        End If
            Designation = ""
    End If
Next i
Exit Function
MsgError:
FunError 2, RangeTitre.Fields(i).Name, MyName
Resume Next
End Function

Public Function FunInsBlock(PathName, InsertPoint, Name, Optional Rotation As Double, Optional XScaleFactor As Double, Optional YScaleFactor As Double, Optional ZScaleFactor As Double) As AcadBlockReference
On Error GoTo GesERR
ErrInsert = False
    ' Create the attribute definition object in model space
    Set FunInsBlock = ActiveDocument.ModelSpace.InsertBlock(InsertPoint, PathName, 1#, 1#, 1#, 0#)
   Dim layerObj As AcadLayer
   a = FunInsBlock.Name
  e = FunInsBlock.GetAttributes
  FunInsBlock.Rotation = Rotation
  If XScaleFactor = 0 Then XScaleFactor = 1
   If YScaleFactor = 0 Then YScaleFactor = 1
   If ZScaleFactor = 0 Then ZScaleFactor = 1
  FunInsBlock.XScaleFactor = XScaleFactor
   FunInsBlock.YScaleFactor = YScaleFactor
   FunInsBlock.ZScaleFactor = ZScaleFactor
'   If Trim("" & Name) <> "" Then
'    ActiveDocument.Blocks(FunInsBlock.Name).Name = Name
'    Else
'    Debug.Print ActiveDocument.Blocks(FunInsBlock.Name).Name
'    End If

    AutoApp.ZoomAll
    
    Exit Function
GesERR:
    FunError 6, "*", PathName & vbCrLf & Err.Description
    ErrInsert = True
End Function


Function DirNUMEROFIL(Path As String, Index As Long) As String
    Dim MyDir As String
    Dim IndexDir As Long
    Dim fso As New FileSystemObject
    DirNUMEROFIL = ""
    MyDir = ""
     
    For IndexDir = 0 To 3
        If fso.FileExists(Path & "NUMEROFIL" & CStr(IndexDir + Index) & ".dwg") = True Then
            MyDir = Path & "NUMEROFIL" & CStr(IndexDir + Index) & ".dwg"
            Exit For
        End If
               
    Next IndexDir
    If Trim(MyDir) = "" Then Exit Function
    DirNUMEROFIL = MyDir
    Set fso = Nothing
End Function
Public Function FunError(NumErr As Long, Lib1 As String, MSG As String, Optional Lib2 As String)
'Dim Msg As String
Dim Sql As String
If Trim("" & Lib1) = "" Then Exit Function
If JobError = 0 Then JobError = AtrbNumError
MSG = MsgErreur(NumErr, Lib1, Lib2, MSG)
Sql = "INSERT INTO T_Error ( JobError, ValError ) "
Sql = Sql & "values(" & JobError & ",'" & MSG & "' );"
Con.Exequte Sql

End Function
Public Function AfficheErreur(Path As String, Entete)
    Dim NuFichier As Long
    Dim Text
    Dim MyTxtErr
    Dim Sql As String
    Dim RsErreur As Recordset
    Dim Fichier As String
    NuFichier = FreeFile
    
    Text = ""
    Sql = "SELECT T_Error.ValError FROM T_Error "
    Sql = Sql & "WHERE T_Error.JobError=" & JobError & ";"
   Con.OpenConnetion db
    Set RsErreur = Con.OpenRecordSet(Sql)
    While RsErreur.EOF = False
        Text = Text & RsErreur!ValError & vbCrLf
        RsErreur.MoveNext
    Wend
    Set RsErreur = Con.CloseRecordSet(RsErreur)
    If Trim("" & Text) = "" Then Exit Function
    
    Dim fso As New FileSystemObject

    MyTxtErr = Entete & Text
    pathUser = Environ("USERPROFILE")
    pathUser = pathUser + "\Mes Documents"
    
    If fso.FolderExists(Path & "RepErrorLog") = False Then
        fso.CreateFolder Path & "RepErrorLog"
    End If
    Fichier = Path & "RepErrorLog\Error_" & Format(Now, "yyyy-mm-dd_hh_mm_ss") & ".log"
    
    While fso.FileExists(Fichier) = True
        Fichier = Path & "RepErrorLog\Error_" & Format(Now, "yyyy-mm-dd_hh_mm_ss") & ".log"
    
    Wend
    Open Fichier For Output As #NuFichier
    Print #NuFichier, MyTxtErr
    Close #NuFichier
    Sql = "DELETE T_Error.* FROM T_Error "
    Sql = Sql & "WHERE T_Error.JobError=" & JobError & ";"
    Con.Exequte Sql
    Set fso = Nothing
    Shell "notepad.exe " & Fichier, vbMaximizedFocus
End Function
 
Public Function MyReplace(strVal As String) As String
MyReplace = strVal
MyReplace = Replace(MyReplace, "'", "''")
MyReplace = Replace(MyReplace, Chr(34), Chr(34) & Chr(34))
'MyReplace = Replace(MyReplace, vbCrLf, " ;")
End Function
Public Function MyReplaceDate(strVal As String) As String
    If Trim(strVal) = "" Then
        MyReplaceDate = "NULL"
    Else
        MyReplaceDate = "#" & strVal & "#"
    End If
    
End Function

Public Sub OpenFichier(Fichier)

    Dim MyDocument As AutoCAD.AcadDocument

    Set MyDocument = AutoApp.Documents.Open(Fichier)
    MyDocument.Activate
End Sub
Public Sub SaveAs(Fichier)
On Error Resume Next

     AutoApp.ActiveDocument.ActiveLayer = AutoApp.ActiveDocument.Layers(1)
        AutoApp.ActiveDocument.PurgeAll
    AutoApp.ActiveDocument.SaveAs Fichier, acR15_dwg
    If Err Then MsgBox Err.Description
    Err.Clear
End Sub
Public Sub CloseDocument()
    AutoApp.ActiveDocument.Close
End Sub
Public Function IsConnecteurs(Attributes As Variant) As Boolean
    Dim Table(5) As String
    Dim Trouve As Boolean
Table(0) = "DESIGNATION"
Table(1) = "POS"
Table(2) = "N°"
Table(3) = "CODE_APP"
Table(4) = "PRECO1"
Table(5) = "PRECO2"
'Table(6) = "FIL"
    IsConnecteurs = True
    
      For i = LBound(Table) To UBound(Table)
        For i2 = LBound(Attributes) To UBound(Attributes)
            If Table(i) = PRECO(UCase("" & Attributes(i2).TagString), True) Then
                Trouve = True
                Exit For
            Else
                Trouve = False
            End If
           
        Next i2
         If Trouve = False Then
                  IsConnecteurs = False
                Exit Function
            End If
      Next i
End Function
Public Function IsCartoucheClient(Attributes As Variant) As Boolean
    Dim Table(6) As String
    Dim Trouve As Boolean
Table(0) = "DESIGN.1.CART.RENAULT"
Table(1) = "DESGN.1.ANGL.CART.REN"
Table(2) = "REF.PF.CART.RENAULT"
Table(3) = "IND.PF"
Table(4) = "REF.PLAN.INDUSTRIEL"
Table(5) = "IND.PI"
Table(6) = "REF.PIECE.CART.RENAULT"
    IsCartoucheClient = True
    
      For i = LBound(Table) To UBound(Table)
        For i2 = LBound(Attributes) To UBound(Attributes)
            If Table(i) = UCase("" & Attributes(i2).TagString) Then
                Trouve = True
                Exit For
            Else
                Trouve = False
            End If
           
        Next i2
         If Trouve = False Then
                  IsCartoucheClient = False
                Exit Function
            End If
      Next i
End Function
Public Function IsCartoucheEncelade(Attributes As Variant) As Boolean
    Dim Table(6) As String
    Dim Trouve As Boolean
Table(0) = ".NOM.DU.CLIENT"
Table(1) = ".RESPONSABLE.CLIENT"
Table(2) = ".NOM.DU.PROJET"
Table(3) = ".VAGUE"
Table(4) = ".DESIGNATION.LIGNE.1"
Table(5) = ".OPTION.ET.DIVERSITE"
Table(6) = "REFERENCE.PLAN.CLIENT"
    IsCartoucheEncelade = True
    
      For i = LBound(Table) To UBound(Table)
        For i2 = LBound(Attributes) To UBound(Attributes)
            If Table(i) = UCase("" & Attributes(i2).TagString) Then
                Trouve = True
                Exit For
            Else
                Trouve = False
            End If
           
        Next i2
         If Trouve = False Then
                  IsCartoucheEncelade = False
                Exit Function
            End If
      Next i
End Function


Public Function IsNOMBRE_FILS(Attributes As Variant) As Boolean
    Dim Table(0) As String
    
Table(0) = "_FILS"
   IsNOMBRE_FILS = True
    

   For i = LBound(Table) To UBound(Table)
        For i2 = LBound(Attributes) To UBound(Attributes)
            If Table(i) = PRECO(UCase("" & Attributes(i2).TagString), True) Then
                Trouve = True
                Exit For
            Else
                Trouve = False
            End If
           
        Next i2
         If Trouve = False Then
                  IsNOMBRE_FILS = False
                Exit Function
            End If
      Next i
End Function

Public Function IsEpissures(Attributes As Variant) As Boolean
    Dim Table(6) As String
    
Table(0) = "DESIGNATION"
Table(1) = "POS"
Table(2) = "N°"
Table(3) = "CODE_APP"
Table(4) = "PRECO1"
Table(5) = "PRECO2"
Table(6) = "FILG1"


    IsEpissures = True
    

   For i = LBound(Table) To UBound(Table)
        For i2 = LBound(Attributes) To UBound(Attributes)
            If Table(i) = PRECO(UCase("" & Attributes(i2).TagString)) Then
                Trouve = True
                Exit For
            Else
                Trouve = False
            End If
           
        Next i2
         If Trouve = False Then
                  IsEpissures = False
                Exit Function
            End If
      Next i
      
End Function
Public Function IsTableauFils(Attributes As Variant) As Boolean
    Dim Table(13) As String
    Table(0) = UCase("LIAI")
    Table(1) = UCase("Designation")
    Table(2) = UCase("Fil")
    Table(3) = UCase("SECT")
    Table(4) = UCase("CO")
    Table(5) = UCase("CO")
    Table(6) = UCase("ISO")
    Table(7) = UCase("POS")
    Table(8) = UCase("Con")
    Table(9) = UCase("VOIE")
    Table(10) = UCase("POS")
    Table(11) = UCase("Con")
    Table(12) = UCase("VOIE")
    Table(13) = UCase("LONG")
    IsTableauFils = True
    For i = LBound(Attributes) To UBound(Attributes)
        If Trim(UCase(Attributes(i).TagString)) <> Trim(Table(i)) Then
            IsTableauFils = False
            Exit Function
        End If
    Next i
End Function
Public Function IsEnteteTableauFils(Attributes As Variant) As Boolean
    Dim Table(12) As String
    Table(0) = UCase("LIAI")
    Table(1) = UCase("DESIGNATION")
    Table(2) = UCase("FIL")
    Table(3) = UCase("SECT")
    Table(4) = UCase("CO")
    Table(5) = UCase("ISO")
    Table(6) = UCase("POS")
    Table(7) = UCase("CON")
    Table(8) = UCase("VOIE")
    Table(9) = UCase("POS")
    Table(10) = UCase("CON")
    Table(11) = UCase("VOIE")
    Table(12) = UCase("LONG")
'    Table(13) = UCase("LONG")
    IsEnteteTableauFils = True
    

    For i = LBound(Attributes) To UBound(Attributes)
        If Trim(UCase(Attributes(i).TagString)) <> Trim(Table(i)) Then
            IsEnteteTableauFils = False
            Exit Function
        End If
    Next i
End Function

Public Function PathArchive(PathRacicine As String, Client As String, CleAc As String, Piece As String, MyType As String, Fichier, IdPieces As Long) As String
Dim fso As New FileSystemObject
Dim Sql As String
Dim Rs As Recordset
Piece = Replace(Piece, "/", "_", 1)
Piece = Replace(Piece, ":", "", 1)
Piece = Replace(Piece, ".", "", 1)

Fichier = Replace(Fichier, "/", "_", 1)
Fichier = Replace(Fichier, ":", "", 1)
Fichier = Replace(Fichier, ".", "", 1)

If fso.FolderExists(PathRacicine) = False Then
    fso.CreateFolder PathRacicine
End If
If Client <> "" Then Client = "\" & Client
If fso.FolderExists(PathRacicine & Client) = False Then
    fso.CreateFolder PathRacicine & Client
End If

If fso.FolderExists(PathRacicine & Client & "\PI") = False Then
    fso.CreateFolder PathRacicine & Client & "\PI"
End If
If fso.FolderExists(PathRacicine & Client & "\PI\" & CleAc) = False Then
    fso.CreateFolder PathRacicine & Client & "\PI\" & CleAc
End If
If fso.FolderExists(PathRacicine & Client & "\PI\" & CleAc & "\" & Piece) = False Then
    fso.CreateFolder PathRacicine & Client & "\PI\" & CleAc & "\" & Piece
End If

Select Case UCase(MyType)
    Case "PL"
        PathArchive = Client & "\PI\" & CleAc & "\" & Piece & "\12-PL\"
    Case "OU"
        PathArchive = Client & "\PI\" & CleAc & "\" & Piece & "\12-OU\"
    Case "LI"
        PathArchive = Client & "\PI\" & CleAc & "\" & Piece & "\12-LI\"
    Case "PI"
End Select
If fso.FolderExists(PathRacicine & PathArchive) = False Then
    fso.CreateFolder PathRacicine & PathArchive
End If
PathArchive = PathArchive & Fichier

'
'    Sql = "SELECT DISTINCT  T_indiceProjet.Id "
'    Sql = Sql & "FROM T_Projet INNER JOIN (T_indiceProjet INNER JOIN Connecteurs ON T_indiceProjet.Id = Connecteurs.Id_IndiceProjet) ON T_Projet.id = T_indiceProjet.IdProjet "
'    Sql = Sql & "WHERE T_Projet.Projet='" & varProjet & "' "
'    Sql = Sql & "AND T_indiceProjet.Li='" & CartoucheEncelade.CombLi.List(CartoucheEncelade.CombLi.ListIndex, 1) & "';"
'Set Rs = Con.OpenRecordSet(Sql)
Con.OpenConnetion db
    Sql = "UPDATE T_indiceProjet SET T_indiceProjet." & UCase(MyType) & "AutoCadSave = '" & MyReplace(PathArchive) & "', T_indiceProjet.NbErr = " & NbError & " "
    Sql = Sql & "WHERE T_indiceProjet.Id=" & IdPieces & ";"
    Con.Exequte Sql

PathArchive = PathRacicine & PathArchive
End Function

Public Function DelAttribues(Attributes As Variant)
 For i = LBound(Attributes) To UBound(Attributes)
    Attributes(i).TextString = ""
    
 Next
End Function
Public Function IsVignette(Attributes As Variant)
    Dim Table(5) As String
    Table(2) = UCase("DESIGNATION.HAUT")
    Table(0) = UCase("CODE_APP")
    Table(1) = UCase("N°")
    Table(3) = UCase("DESIGNATION.BAS")
    Table(4) = UCase("DESIGNATION.GAUCHE")
    Table(5) = UCase("DESIGNATION.DROITE")
  
    IsVignette = True
     For i = LBound(Table) To UBound(Table)
        For i2 = LBound(Attributes) To UBound(Attributes)
            If Table(i) = PRECO(UCase("" & Attributes(i2).TagString), True) Then
                Trouve = True
                Exit For
            Else
                Trouve = False
            End If
           
        Next i2
         If Trouve = False Then
                  IsVignette = False
                Exit Function
            End If
      Next i
End Function
Public Function IsVignetteEtiquette(Attributes As Variant)
    Dim Table(3) As String
    Dim Trouve As Boolean
    Table(0) = UCase("FIL1")
    Table(1) = UCase("FIL2")
    Table(2) = UCase("FIL3")
    Table(3) = UCase("FIL4")
  
    IsVignetteEtiquette = True
   
    Trouve = False
    For i2 = LBound(Attributes) To UBound(Attributes)
        If Trim(UCase(Attributes(i2).TagString)) = "N°" Then
           Trouve = True
           Exit For
        End If
     Next i2
        If Trouve = True Then
         IsVignetteEtiquette = False
            Exit Function
        End If
    For i = LBound(Table) To UBound(Table)
    Trouve = False
    For i2 = LBound(Attributes) To UBound(Attributes)
        If Trim(UCase(Attributes(i2).TagString)) = Trim(Table(i)) Then
           Trouve = True
           Exit For
        End If
     Next i2
        If Trouve = False Then
         IsVignetteEtiquette = False
            Exit Function
        End If
    Next i
End Function

Public Function IsVignetteEPISSURE(Attributes As Variant)
    Dim Table(0) As String
    Table(0) = UCase("EPISSURE")
  
    IsVignetteEPISSURE = True
   ' For i = LBound(Attributes) To UBound(Attributes)
     '   If Trim(UCase(Attributes(i).TagString)) = Trim(Table(i)) Then
    '        IsVignetteEPISSURE = False
    '        Exit Function
    '    End If
    'Next i
    
       For i = LBound(Table) To UBound(Table)
        For i2 = LBound(Attributes) To UBound(Attributes)
            If Table(i) = PRECO(UCase("" & Attributes(i2).TagString), True) Then
                Trouve = True
                Exit For
            Else
                Trouve = False
            End If
           
        Next i2
         If Trouve = False Then
                  IsVignetteEPISSURE = False
                Exit Function
            End If
      Next i
   
    
    
    
End Function
Public Sub MyAccess(IdPieces As Long)
    Dim RsLigne As Recordset
    Dim Sql As String
    Dim fso As New FileSystemObject
    InsertPointLigneTableau_fils(0) = -1096.5549: InsertPointLigneTableau_fils(1) = -76.8274: InsertPointLigneTableau_fils(2) = 0
'    Sql = "SELECT Ligne_Tableau_fils.LIAI, Ligne_Tableau_fils.DESIGNATION, Ligne_Tableau_fils.FIL, Ligne_Tableau_fils.SECT, Ligne_Tableau_fils.TEINT, Ligne_Tableau_fils.TEINT2, Ligne_Tableau_fils.ISO, Ligne_Tableau_fils.POS, Ligne_Tableau_fils.FA, Ligne_Tableau_fils.VOI, Ligne_Tableau_fils.POS2, Ligne_Tableau_fils.FA2, Ligne_Tableau_fils.VOI2, Ligne_Tableau_fils.LONG, Ligne_Tableau_fils.APP, Ligne_Tableau_fils.APP2 "
'    Sql = Sql & "FROM T_Projet INNER JOIN (T_indiceProjet INNER JOIN Ligne_Tableau_fils ON T_indiceProjet.Id = Ligne_Tableau_fils.Id_IndiceProjet) ON T_Projet.id = T_indiceProjet.IdProjet "
'    Sql = Sql & "WHERE T_Projet.Projet='" & varProjet & "' "
'    Sql = Sql & "AND T_indiceProjet.LI='" & MyReplace(CartoucheEncelade.CombLi.List(CartoucheEncelade.CombLi.ListIndex, 1)) & "' "
'    Sql = Sql & "ORDER BY Ligne_Tableau_fils.FIL;"
'

Sql = "SELECT Ligne_Tableau_fils.LIAI, Ligne_Tableau_fils.DESIGNATION,  "
    Sql = Sql & "Ligne_Tableau_fils.FIL, Ligne_Tableau_fils.SECT,  "
    Sql = Sql & "Ligne_Tableau_fils.TEINT, Ligne_Tableau_fils.TEINT2,  "
    Sql = Sql & "Ligne_Tableau_fils.ISO, Ligne_Tableau_fils.POS,  "
    Sql = Sql & "Ligne_Tableau_fils.FA, Ligne_Tableau_fils.VOI,  "
    Sql = Sql & "Ligne_Tableau_fils.POS2, Ligne_Tableau_fils.FA2,  "
    Sql = Sql & "Ligne_Tableau_fils.VOI2, Ligne_Tableau_fils.LONG,  "
    Sql = Sql & "Ligne_Tableau_fils.APP, Ligne_Tableau_fils.APP2,  "
    Sql = Sql & "T_indiceProjet.Id_Pieces "
    Sql = Sql & "FROM T_indiceProjet INNER JOIN Ligne_Tableau_fils  "
    Sql = Sql & "ON T_indiceProjet.Id = Ligne_Tableau_fils.Id_IndiceProjet "
    Sql = Sql & "WHERE T_indiceProjet.Id_Pieces=" & IdPieces & " "
    Sql = Sql & "ORDER BY Ligne_Tableau_fils.FIL;"

    Set RsLigne = Con.OpenRecordSet(Sql)
    While RsLigne.EOF = False
        NbConnecteur = NbConnecteur + 1
        RsLigne.MoveNext
    Wend
    If Val(NbConnecteur) <> 0 Then
    RsLigne.MoveFirst
    End If
     FormBarGrah.ProgressBar1.Value = 0
    If Val(NbConnecteur) <> 0 Then
     FormBarGrah.ProgressBar1.Max = 1 + NbConnecteur
    Else
         FormBarGrah.ProgressBar1.Max = 1 + 1
    End If
     FormBarGrah.ProgressBar1Caption.Caption = "Chargement de la liste de fils"

    While RsLigne.EOF = False
         FormBarGrah.ProgressBar1.Value = FormBarGrah.ProgressBar1.Value + 1
        DoEvents
        AutoApp.ZoomAll

        ReDim Tableau(RsLigne.Fields.Count)
        For Col = 0 To RsLigne.Fields.Count - 1
            DoEvents
            Tableau(Col) = "" & RsLigne.Fields(Col)
        Next Col
     
        RenseigneConnecteurBroches RsLigne
        Row = Row + 1
        If NbLignes = 100 Then
            InsertPointLigneTableau_fils(1) = -76.8274: InsertPointLigneTableau_fils(0) = DecalInsertPointLigneTableau_fils_Gauche(InsertPointLigneTableau_fils(0), 281.7719)
            NbLignes = 0
        End If

        If NbLignes = 0 Then
            If fso.FileExists(TableauPath.Item("PathBlocs") & "LIGNE TABLEAU DES FILS_RD.dwg") = False Then
                MsgBox "err"
            End If
            Set NewBlock = FunInsBlock(TableauPath.Item("PathBlocs") & "LIGNE TABLEAU DES FILS_RD.dwg", InsertPointLigneTableau_fils, "E" & CStr(Row))
            InsertPointLigneTableau_fils(1) = DecalInsertPointLigneTableau_fils_Bas(InsertPointLigneTableau_fils(1), 6.8274)
        End If
        If fso.FileExists(TableauPath.Item("PathBlocs") & "LIGNE TABLEAU DES FILS.dwg") = False Then
            MsgBox "err"
        End If
        Set NewBlock = FunInsBlock(TableauPath.Item("PathBlocs") & "LIGNE TABLEAU DES FILS.dwg", InsertPointLigneTableau_fils, "L" & CInt(Row))
        a = NewBlock.GetAttributes
        InsertPointLigneTableau_fils(1) = DecalInsertPointLigneTableau_fils_Bas(InsertPointLigneTableau_fils(1), 6.8274)

        NbLignes = NbLignes + 1
        On Error GoTo Error1
        Lib1 = RsLigne.Fields(2)
        Lib2 = "" & RsLigne.Fields("APP")
        TableauDeConnecteurs(CLng(CollectionCon("" & RsLigne.Fields("APP")))).indexFile = TableauDeConnecteurs(CLng(CollectionCon("" & RsLigne.Fields("APP")))).indexFile + 1
        Lib1 = ""
        Lib2 = ""
        ReDim Preserve TableauDeConnecteurs(CLng(CollectionCon("" & RsLigne.Fields("APP")))).TableauFile(TableauDeConnecteurs(CLng(CollectionCon("" & RsLigne.Fields("APP")))).indexFile)
        TableauDeConnecteurs(CLng(CollectionCon("" & RsLigne.Fields("APP")))).TableauFile(TableauDeConnecteurs(CLng(CollectionCon("" & RsLigne.Fields("APP")))).indexFile) = RsLigne.Fields(2)

        Lib1 = RsLigne.Fields(2)
        Lib2 = "" & RsLigne.Fields("APP2")
        TableauDeConnecteurs(CLng(CollectionCon("" & RsLigne.Fields("APP2")))).indexFile = TableauDeConnecteurs(CLng(CollectionCon("" & RsLigne.Fields("APP2")))).indexFile + 1
        Lib1 = ""
        Lib2 = ""
        ReDim Preserve TableauDeConnecteurs(CLng(CollectionCon("" & RsLigne.Fields("APP2")))).TableauFile(TableauDeConnecteurs(CLng(CollectionCon("" & RsLigne.Fields("APP2")))).indexFile)

        TableauDeConnecteurs(CLng(CollectionCon("" & RsLigne.Fields("APP2")))).TableauFile(TableauDeConnecteurs(CLng(CollectionCon("" & RsLigne.Fields("APP2")))).indexFile) = RsLigne.Fields(2)

        a = RsLigne.Fields(0)
        funAttributesLigne_Tableau_fils NewBlock.Name, NewBlock.GetAttributes, Tableau, RsLigne.Fields.Count - 1
        RsLigne.MoveNext
    Wend
    If NbConnecteur > 0 Then
        Set NewBlock = FunInsBlock(TableauPath.Item("PathBlocs") & "Nombre_fils.dwg", InsertPointLigneTableau_fils, "N1")
        attri = NewBlock.GetAttributes
        attri(0).TextString = NbConnecteur
     End If
   
    SacnConnecteur
'    SaveAs "c:\RD\rd"
Fin:
    Set Myrange = Nothing
    Set MySheet = Nothing
    ReDim TableauDeConnecteurs(0)
    Set fso = Nothing
    Exit Sub
Error1:
    FunError 3, CStr("" & Lib1), CStr("" & Lib2)
    Resume Next

End Sub

Public Sub SacnConnecteur()
    Dim Index As Long
    Dim NewBlock  As AcadBlockReference
    Dim MyFichier As String
     FormBarGrah.ProgressBar1.Value = 0
    If UBound(TableauDeConnecteurs) > 0 Then
         FormBarGrah.ProgressBar1.Max = 1 + UBound(TableauDeConnecteurs)
     Else
         FormBarGrah.ProgressBar1.Max = 1 + 1
     End If
     FormBarGrah.ProgressBar1Caption.Caption = "Chargement des vignettes"
    For Index = 1 To UBound(TableauDeConnecteurs)
         FormBarGrah.ProgressBar1.Value = FormBarGrah.ProgressBar1.Value + 1
        DoEvents
        
        If TableauDeConnecteurs(Index).ConnecteurExiste = True Then
            If TableauDeConnecteurs(Index).indexFile > 0 Then
                TableauDeConnecteurs(Index).TableauFile = TriTableau(TableauDeConnecteurs(Index).TableauFile)
                MyFichier = DirNUMEROFIL(TableauPath.Item("PathNUMEROFIL"), TableauDeConnecteurs(Index).indexFile)
                If Trim(MyFichier) <> "" Then
                    InsertionPoint = TableauDeConnecteurs(Index).NewVignette.InsertionPoint
                    InsertPointLigneTableau_fils(0) = InsertionPoint(0) + 18.022: InsertPointLigneTableau_fils(1) = InsertionPoint(1) + 16.041: InsertPointLigneTableau_fils(2) = InsertionPoint(2)
                    Set NewBlock = FunInsBlock(MyFichier, InsertPointLigneTableau_fils, "NF" & CInt(Index))
                    AttribueLibV NewBlock, Index
                Else
                
                End If
            End If
        End If
    Next Index

End Sub
Public Function ChargeCartoucheEncelade(IdIndiceProjet As Long, MyType As String, Optional OuOk As Boolean) As Boolean

    Dim fso As New FileSystemObject
    Dim Sql As String
Dim Rs As Recordset
Dim Status As String
Sql = "SELECT RqCartouche.* "
Sql = Sql & "FROM RqCartouche "
Sql = Sql & "WHERE RqCartouche.T_indiceProjet.Id=" & IdIndiceProjet & ";"
Set Rs = Con.OpenRecordSet(Sql)
If Rs.EOF = True Then Exit Function
Status = "" & Rs!Status
    CartoucheCleient = False
    InsertPointLigneTableau_fils(0) = -312#: InsertPointLigneTableau_fils(1) = 20: InsertPointLigneTableau_fils(2) = 0
    If fso.FileExists(TableauPath.Item("PathBlocs") & LeCartoucheE) = False Then
        Set fso = Nothing
        Exit Function
    End If
    
    Set NewBlock = FunInsBlock(TableauPath.Item("PathBlocs") & LeCartoucheE, InsertPointLigneTableau_fils, "LeCartouche1E")
    AttClent = NewBlock.GetAttributes

    Set AttribuCartouche = ColectionAttribueConecteur(NewBlock.GetAttributes)
   AttClent(AttribuCartouche(".NOM.DU.Client")).TextString = "" & Rs!Client
    AttClent(AttribuCartouche(".RESPONSABLE.Client")).TextString = "" & Rs!Responsable
    AttClent(AttribuCartouche(".NOM.DU.Projet")).TextString = "" & Rs!Projet
    AttClent(AttribuCartouche(".VAGUE")).TextString = "" & Rs!Vague
    AttClent(AttribuCartouche(".DESIGNATION.LIGNE.1")).TextString = Replace("" & Rs!Ensemble, Chr(13), "")
'    AttClent(AttribuCartouche(".DESIGNATION.LIGNE.2")).TextString = "" ' & Rs!Client
    AttClent(AttribuCartouche(".OPTION.ET.DIVERSITE")).TextString = "" & Rs!Equipement
    If OuOk = True Then
        AttClent(AttribuCartouche("Reference.PLAN.Client")).TextString = "" & Rs!OU
    Else
        AttClent(AttribuCartouche("Reference.PLAN.Client")).TextString = "" & Rs!Pl
    
    End If
    AttClent(AttribuCartouche("INDICE")).TextString = "" & Rs!Indice
    AttClent(AttribuCartouche("Reference.PLAN.FONCTIONNEL")).TextString = "" & Rs!RefPf
    AttClent(AttribuCartouche("RF2")).TextString = "" ' & Rs!Client
    AttClent(AttribuCartouche("Reference.ENCELADE")).TextString = "" & Rs!Pi
    AttClent(AttribuCartouche("RF1")).TextString = "" & Rs!Indice
    AttClent(AttribuCartouche("DESSINE.PAR")).TextString = "" & Rs!DessineNOM
    AttClent(AttribuCartouche("DESSINELE")).TextString = "" & Rs!DessineDate
    AttClent(AttribuCartouche("VERIFIE.PAR")).TextString = "" & Rs!VerifieNom
    AttClent(AttribuCartouche("VERIFIELE")).TextString = "" & Rs!VerifieDate
    AttClent(AttribuCartouche("APPROUVE.PAR")).TextString = "" & Rs!ApprouveNom
    AttClent(AttribuCartouche("APPROUVELE")).TextString = "" & Rs!ApprouveDate
    AttClent(AttribuCartouche(".MASSE")).TextString = "" & Rs!Masse
    AttClent(AttribuCartouche("ETAT")).TextString = Status
    AttClent(AttribuCartouche("X/X")).TextString = "1/4"
    
    InsertPointLigneTableau_fils(0) = 876#: InsertPointLigneTableau_fils(1) = 20#: InsertPointLigneTableau_fils(2) = 0
    Set NewBlock = FunInsBlock(TableauPath.Item("PathBlocs") & LeCartoucheE, InsertPointLigneTableau_fils, "LeCartouche2E")
    AttClent = NewBlock.GetAttributes
    Set AttribuCartouche = ColectionAttribueConecteur(NewBlock.GetAttributes)
     AttClent(AttribuCartouche(".NOM.DU.Client")).TextString = "" & Rs!Client
    AttClent(AttribuCartouche(".RESPONSABLE.Client")).TextString = "" & Rs!Responsable
    AttClent(AttribuCartouche(".NOM.DU.Projet")).TextString = "" & Rs!Projet
    AttClent(AttribuCartouche(".VAGUE")).TextString = "" & Rs!Vague
    AttClent(AttribuCartouche(".DESIGNATION.LIGNE.1")).TextString = Replace("" & Rs!Ensemble, Chr(13), "")
'    AttClent(AttribuCartouche(".DESIGNATION.LIGNE.2")).TextString = "" ' & Rs!Client
    AttClent(AttribuCartouche(".OPTION.ET.DIVERSITE")).TextString = "" & Rs!Equipement
    If OuOk = True Then
        AttClent(AttribuCartouche("Reference.PLAN.Client")).TextString = "" & Rs!OU
    Else
        AttClent(AttribuCartouche("Reference.PLAN.Client")).TextString = "" & Rs!Pl
    
    End If
    AttClent(AttribuCartouche("INDICE")).TextString = "" & Rs!Indice
    AttClent(AttribuCartouche("Reference.PLAN.FONCTIONNEL")).TextString = "" & Rs!RefPf
    AttClent(AttribuCartouche("RF2")).TextString = "" ' & Rs!Client
    AttClent(AttribuCartouche("Reference.ENCELADE")).TextString = "" & Rs!Pi
    AttClent(AttribuCartouche("RF1")).TextString = "" & Rs!Indice
    AttClent(AttribuCartouche("DESSINE.PAR")).TextString = "" & Rs!DessineNOM
    AttClent(AttribuCartouche("DESSINELE")).TextString = "" & Rs!DessineDate
    AttClent(AttribuCartouche("VERIFIE.PAR")).TextString = "" & Rs!VerifieNom
    AttClent(AttribuCartouche("VERIFIELE")).TextString = "" & Rs!VerifieDate
    AttClent(AttribuCartouche("APPROUVE.PAR")).TextString = "" & Rs!ApprouveNom
    AttClent(AttribuCartouche("APPROUVELE")).TextString = "" & Rs!ApprouveDate
    AttClent(AttribuCartouche(".MASSE")).TextString = "" & Rs!Masse
    AttClent(AttribuCartouche("ETAT")).TextString = Status
    AttClent(AttribuCartouche("X/X")).TextString = "2/4"

    
    InsertPointLigneTableau_fils(0) = 876#: InsertPointLigneTableau_fils(1) = -820#: InsertPointLigneTableau_fils(2) = 0
    Set NewBlock = FunInsBlock(TableauPath.Item("PathBlocs") & LeCartoucheE, InsertPointLigneTableau_fils, "LeCartouche3E")
    AttClent = NewBlock.GetAttributes
    Set AttribuCartouche = ColectionAttribueConecteur(NewBlock.GetAttributes)
 
'
 AttClent(AttribuCartouche(".NOM.DU.Client")).TextString = "" & Rs!Client
    AttClent(AttribuCartouche(".RESPONSABLE.Client")).TextString = "" & Rs!Responsable
    AttClent(AttribuCartouche(".NOM.DU.Projet")).TextString = "" & Rs!Projet
    AttClent(AttribuCartouche(".VAGUE")).TextString = "" & Rs!Vague
    AttClent(AttribuCartouche(".DESIGNATION.LIGNE.1")).TextString = Replace("" & Rs!Ensemble, Chr(13), "")
'    AttClent(AttribuCartouche(".DESIGNATION.LIGNE.2")).TextString = "" ' & Rs!Client
    AttClent(AttribuCartouche(".OPTION.ET.DIVERSITE")).TextString = "" & Rs!Equipement
    If OuOk = True Then
        AttClent(AttribuCartouche("Reference.PLAN.Client")).TextString = "" & Rs!OU
    Else
        AttClent(AttribuCartouche("Reference.PLAN.Client")).TextString = "" & Rs!Pl
    
    End If
    AttClent(AttribuCartouche("INDICE")).TextString = "" & Rs!Indice
    AttClent(AttribuCartouche("Reference.PLAN.FONCTIONNEL")).TextString = "" & Rs!RefPf
    AttClent(AttribuCartouche("RF2")).TextString = "" ' & Rs!Client
    AttClent(AttribuCartouche("Reference.ENCELADE")).TextString = "" & Rs!Pi
    AttClent(AttribuCartouche("RF1")).TextString = "" & Rs!Indice
    AttClent(AttribuCartouche("DESSINE.PAR")).TextString = "" & Rs!DessineNOM
    AttClent(AttribuCartouche("DESSINELE")).TextString = "" & Rs!DessineDate
    AttClent(AttribuCartouche("VERIFIE.PAR")).TextString = "" & Rs!VerifieNom
    AttClent(AttribuCartouche("VERIFIELE")).TextString = "" & Rs!VerifieDate
    AttClent(AttribuCartouche("APPROUVE.PAR")).TextString = "" & Rs!ApprouveNom
    AttClent(AttribuCartouche("APPROUVELE")).TextString = "" & Rs!ApprouveDate
    AttClent(AttribuCartouche(".MASSE")).TextString = "" & Rs!Masse
    AttClent(AttribuCartouche("ETAT")).TextString = Status
    AttClent(AttribuCartouche("X/X")).TextString = "4/4"


    InsertPointLigneTableau_fils(0) = -312#: InsertPointLigneTableau_fils(1) = -820#: InsertPointLigneTableau_fils(2) = 0
    Set NewBlock = FunInsBlock(TableauPath.Item("PathBlocs") & LeCartoucheE, InsertPointLigneTableau_fils, "LeCartouche4E")
    AttClent = NewBlock.GetAttributes
    Set AttribuCartouche = ColectionAttribueConecteur(NewBlock.GetAttributes)
    AttClent(AttribuCartouche(".NOM.DU.Client")).TextString = "" & Rs!Client
    AttClent(AttribuCartouche(".RESPONSABLE.Client")).TextString = "" & Rs!Responsable
    AttClent(AttribuCartouche(".NOM.DU.Projet")).TextString = "" & Rs!Projet
    AttClent(AttribuCartouche(".VAGUE")).TextString = "" & Rs!Vague
    AttClent(AttribuCartouche(".DESIGNATION.LIGNE.1")).TextString = Replace("" & Rs!Ensemble, Chr(13), "")
'    AttClent(AttribuCartouche(".DESIGNATION.LIGNE.2")).TextString = "" ' & Rs!Client
    AttClent(AttribuCartouche(".OPTION.ET.DIVERSITE")).TextString = "" & Rs!Equipement
    If OuOk = True Then
        AttClent(AttribuCartouche("Reference.PLAN.Client")).TextString = "" & Rs!OU
    Else
        AttClent(AttribuCartouche("Reference.PLAN.Client")).TextString = "" & Rs!Pl
    
    End If
    AttClent(AttribuCartouche("INDICE")).TextString = "" & Rs!Indice
    AttClent(AttribuCartouche("Reference.PLAN.FONCTIONNEL")).TextString = "" & Rs!RefPf
    AttClent(AttribuCartouche("RF2")).TextString = "" ' & Rs!Client
    AttClent(AttribuCartouche("Reference.ENCELADE")).TextString = "" & Rs!Pi
    AttClent(AttribuCartouche("RF1")).TextString = "" & Rs!Indice
    AttClent(AttribuCartouche("DESSINE.PAR")).TextString = "" & Rs!DessineNOM
    AttClent(AttribuCartouche("DESSINELE")).TextString = "" & Rs!DessineDate
    AttClent(AttribuCartouche("VERIFIE.PAR")).TextString = "" & Rs!VerifieNom
    AttClent(AttribuCartouche("VERIFIELE")).TextString = "" & Rs!VerifieDate
    AttClent(AttribuCartouche("APPROUVE.PAR")).TextString = "" & Rs!ApprouveNom
    AttClent(AttribuCartouche("APPROUVELE")).TextString = "" & Rs!ApprouveDate
    AttClent(AttribuCartouche(".MASSE")).TextString = "" & Rs!Masse
    AttClent(AttribuCartouche("ETAT")).TextString = Status
    AttClent(AttribuCartouche("X/X")).TextString = "3/4"
    CartoucheCleient = True
    Set fso = Nothing
End Function
Public Function ChargeCartoucheClient(IdIndiceProjet As Long, MyType As String, Optional OuOk As Boolean) As Boolean
Dim Sql As String
Dim Rs As Recordset
LeCartouche = "CARTOUCHE  RENAULT.dwg"
LeCartoucheE = "CARTOUCHE ENCELADE.dwg"

If boolFormClient = False Then Exit Function
Sql = "SELECT RqCartouche.* "
Sql = Sql & "FROM RqCartouche "
Sql = Sql & "WHERE RqCartouche.T_indiceProjet.Id=" & IdIndiceProjet & ";"
Set Rs = Con.OpenRecordSet(Sql)
If Rs.EOF = True Then Exit Function

    Dim fso As New FileSystemObject
    CartoucheCleient = False
    InsertPointLigneTableau_fils(0) = -165.0409: InsertPointLigneTableau_fils(1) = 126.0753: InsertPointLigneTableau_fils(2) = 0
    If fso.FileExists(TableauPath.Item("PathBlocs") & LeCartouche) = False Then
        Set fso = Nothing
        Exit Function
    End If
    Set NewBlock = FunInsBlock(TableauPath.Item("PathBlocs") & LeCartouche, InsertPointLigneTableau_fils, "LeCartouche1")
    AttClent = NewBlock.GetAttributes

    Set AttribuCartouche = ColectionAttribueConecteur(NewBlock.GetAttributes)
'    a = NewBlock.GetAttributes
'    For iClient = 0 To 16
'        Debug.Print a(iClient).TagString
'    Next iClient
''        ControlTag = Split(MyCARTOUCHE_Client.Controls("txt" & CStr(iClient)).tag, ";")
'        a = MyCARTOUCHE_Client.Controls("txt" & CStr(iClient))
'        AttClent(AttribuCartouche(UCase(ControlTag(0)))).TextString = Replace(MyCARTOUCHE_Client.Controls("txt" & CStr(iClient)), vbCrLf, Right(vbCrLf, 1))
''    Next iClient
'AttClent(AttribuCartouche(".NOM.DU.Client")).TextString = "1/4"
'AttClent(AttribuCartouche(".RESPONSABLE.Client")).TextString = "1/4"
'AttClent(AttribuCartouche(".NOM.DU.Projet")).TextString = "1/4"
'AttClent(AttribuCartouche(".VAGUE")).TextString = "1/4"
'AttClent(AttribuCartouche(".Designation.LIGNE 0.1")).TextString = "1/4"
'AttClent(AttribuCartouche(".Designation.LIGNE 0.2")).TextString = "1/4"
'AttClent(AttribuCartouche(".OPTION.ET.DIVERSITE")).TextString = "1/4"
'AttClent(AttribuCartouche("Reference.PLAN.Client")).TextString = "1/4"
'AttClent(AttribuCartouche("INDICE")).TextString = "1/4"
'AttClent(AttribuCartouche("Reference.PLAN.FONCTIONNEL")).TextString = "1/4"
'AttClent(AttribuCartouche("RF2")).TextString = "1/4"
'AttClent(AttribuCartouche("Reference.ENCELADE")).TextString = "1/4"
'AttClent(AttribuCartouche("RF1")).TextString = "1/4"
'AttClent(AttribuCartouche("DESSINE.PAR")).TextString = "1/4"
'AttClent(AttribuCartouche("DESSINELE")).TextString = "1/4"
'AttClent(AttribuCartouche("VERIFIE.PAR")).TextString = "1/4"
'AttClent(AttribuCartouche("VERIFIELE")).TextString = "1/4"
'AttClent(AttribuCartouche("APPROUVE.PAR")).TextString = "1/4"
'AttClent(AttribuCartouche("APPROUVELE")).TextString = "1/4"
'AttClent(AttribuCartouche(".MASSE")).TextString = "1/4"
'AttClent(AttribuCartouche("X/X")).TextString = "1/4"
'AttClent(AttribuCartouche("ETAT")).TextString = "1/4"


AttClent(AttribuCartouche("DESIGN.1.CART.RENAULT")).TextString = "" & Rs("Ensemble")
AttClent(AttribuCartouche("MASSE")).TextString = "" & Rs("Masse")
AttClent(AttribuCartouche("IND.Pi")).TextString = "" & Rs("Indice")
AttClent(AttribuCartouche("REF.PF.CART.RENAULT")).TextString = "" & Rs("RefPF")
If OuOk = True Then
   
        AttClent(AttribuCartouche("REF.PLAN.INDUSTRIEL")).TextString = "" & Rs!OU
    Else
    
        AttClent(AttribuCartouche("REF.PLAN.INDUSTRIEL")).TextString = "" & Rs!Pl
    
    End If
    
    





AttClent(AttribuCartouche("DESIGN.2.CART.RENAULT")).TextString = ""
AttClent(AttribuCartouche("DESGN.1.ANGL.CART.REN")).TextString = ""
AttClent(AttribuCartouche("DESGN.2.ANGL.CART.REN")).TextString = ""

AttClent(AttribuCartouche("IND.PF")).TextString = ""


AttClent(AttribuCartouche("REF.PIECE.CART.RENAULT")).TextString = ""
AttClent(AttribuCartouche("SERVICE")).TextString = ""
AttClent(AttribuCartouche("UTILISATEURS")).TextString = ""

AttClent(AttribuCartouche("REGLEMENT")).TextString = ""
AttClent(AttribuCartouche("NOTE.BE.1")).TextString = ""
AttClent(AttribuCartouche("NOTE.BE.2")).TextString = ""
AttClent(AttribuCartouche("Num.VISA")).TextString = ""
AttClent(AttribuCartouche("X/X")).TextString = "1/4"




    InsertPointLigneTableau_fils(0) = 1022.9591: InsertPointLigneTableau_fils(1) = 126.0753: InsertPointLigneTableau_fils(2) = 0
    Set NewBlock = FunInsBlock(TableauPath.Item("PathBlocs") & LeCartouche, InsertPointLigneTableau_fils, "LeCartouche2")
    AttClent = NewBlock.GetAttributes
    Set AttribuCartouche = ColectionAttribueConecteur(NewBlock.GetAttributes)

    '
AttClent(AttribuCartouche("DESIGN.1.CART.RENAULT")).TextString = "" & Rs("Ensemble")
AttClent(AttribuCartouche("MASSE")).TextString = "" & Rs("Masse")
AttClent(AttribuCartouche("IND.Pi")).TextString = "" & Rs("Indice")
AttClent(AttribuCartouche("REF.PF.CART.RENAULT")).TextString = "" & Rs("RefPF")
If OuOk = True Then
   
        AttClent(AttribuCartouche("REF.PLAN.INDUSTRIEL")).TextString = "" & Rs!OU
    Else
    
        AttClent(AttribuCartouche("REF.PLAN.INDUSTRIEL")).TextString = "" & Rs!Pl
    
    End If
    
    





AttClent(AttribuCartouche("DESIGN.2.CART.RENAULT")).TextString = ""
AttClent(AttribuCartouche("DESGN.1.ANGL.CART.REN")).TextString = ""
AttClent(AttribuCartouche("DESGN.2.ANGL.CART.REN")).TextString = ""

AttClent(AttribuCartouche("IND.PF")).TextString = ""


AttClent(AttribuCartouche("REF.PIECE.CART.RENAULT")).TextString = ""
AttClent(AttribuCartouche("SERVICE")).TextString = ""
AttClent(AttribuCartouche("UTILISATEURS")).TextString = ""

AttClent(AttribuCartouche("REGLEMENT")).TextString = ""
AttClent(AttribuCartouche("NOTE.BE.1")).TextString = ""
AttClent(AttribuCartouche("NOTE.BE.2")).TextString = ""
AttClent(AttribuCartouche("Num.VISA")).TextString = ""
    AttClent(AttribuCartouche("X/X")).TextString = "2/4"

    InsertPointLigneTableau_fils(0) = 1022.9591: InsertPointLigneTableau_fils(1) = -713.9247: InsertPointLigneTableau_fils(2) = 0
    Set NewBlock = FunInsBlock(TableauPath.Item("PathBlocs") & LeCartouche, InsertPointLigneTableau_fils, "LeCartouche3")
    AttClent = NewBlock.GetAttributes
    Set AttribuCartouche = ColectionAttribueConecteur(NewBlock.GetAttributes)
    '
AttClent(AttribuCartouche("DESIGN.1.CART.RENAULT")).TextString = "" & Rs("Ensemble")
AttClent(AttribuCartouche("MASSE")).TextString = "" & Rs("Masse")
AttClent(AttribuCartouche("IND.Pi")).TextString = "" & Rs("Indice")
AttClent(AttribuCartouche("REF.PF.CART.RENAULT")).TextString = "" & Rs("RefPF")
If OuOk = True Then
   
        AttClent(AttribuCartouche("REF.PLAN.INDUSTRIEL")).TextString = "" & Rs!OU
    Else
    
        AttClent(AttribuCartouche("REF.PLAN.INDUSTRIEL")).TextString = "" & Rs!Pl
    
    End If
    
    





AttClent(AttribuCartouche("DESIGN.2.CART.RENAULT")).TextString = ""
AttClent(AttribuCartouche("DESGN.1.ANGL.CART.REN")).TextString = ""
AttClent(AttribuCartouche("DESGN.2.ANGL.CART.REN")).TextString = ""

AttClent(AttribuCartouche("IND.PF")).TextString = ""


AttClent(AttribuCartouche("REF.PIECE.CART.RENAULT")).TextString = ""
AttClent(AttribuCartouche("SERVICE")).TextString = ""
AttClent(AttribuCartouche("UTILISATEURS")).TextString = ""

AttClent(AttribuCartouche("REGLEMENT")).TextString = ""
AttClent(AttribuCartouche("NOTE.BE.1")).TextString = ""
AttClent(AttribuCartouche("NOTE.BE.2")).TextString = ""
AttClent(AttribuCartouche("Num.VISA")).TextString = ""
    AttClent(AttribuCartouche("X/X")).TextString = "4/4"
    
    InsertPointLigneTableau_fils(0) = -165.0409: InsertPointLigneTableau_fils(1) = -713.9247: InsertPointLigneTableau_fils(2) = 0
    Set NewBlock = FunInsBlock(TableauPath.Item("PathBlocs") & LeCartouche, InsertPointLigneTableau_fils, "LeCartouche4")
    AttClent = NewBlock.GetAttributes
    Set AttribuCartouche = ColectionAttribueConecteur(NewBlock.GetAttributes)
    
AttClent(AttribuCartouche("DESIGN.1.CART.RENAULT")).TextString = "" & Rs("Ensemble")
AttClent(AttribuCartouche("MASSE")).TextString = "" & Rs("Masse")
AttClent(AttribuCartouche("IND.Pi")).TextString = "" & Rs("Indice")
AttClent(AttribuCartouche("REF.PF.CART.RENAULT")).TextString = "" & Rs("RefPF")
If OuOk = True Then
   
        AttClent(AttribuCartouche("REF.PLAN.INDUSTRIEL")).TextString = "" & Rs!OU
    Else
    
        AttClent(AttribuCartouche("REF.PLAN.INDUSTRIEL")).TextString = "" & Rs!Pl
    
    End If
    
    





AttClent(AttribuCartouche("DESIGN.2.CART.RENAULT")).TextString = ""
AttClent(AttribuCartouche("DESGN.1.ANGL.CART.REN")).TextString = ""
AttClent(AttribuCartouche("DESGN.2.ANGL.CART.REN")).TextString = ""

AttClent(AttribuCartouche("IND.PF")).TextString = ""


AttClent(AttribuCartouche("REF.PIECE.CART.RENAULT")).TextString = ""
AttClent(AttribuCartouche("SERVICE")).TextString = ""
AttClent(AttribuCartouche("UTILISATEURS")).TextString = ""

AttClent(AttribuCartouche("REGLEMENT")).TextString = ""
AttClent(AttribuCartouche("NOTE.BE.1")).TextString = ""
AttClent(AttribuCartouche("NOTE.BE.2")).TextString = ""
AttClent(AttribuCartouche("Num.VISA")).TextString = ""

    AttClent(AttribuCartouche("X/X")).TextString = "3/4"
    CartoucheCleient = True
    Set fso = Nothing
End Function
Public Sub Maj(MyControl As Object)
Dim Rs As Recordset
Dim Sql As String
Con.OpenConnetion db
MyControl.Clear
Sql = "SELECT T_Clients.Client, T_Clients.Formulaire "
Sql = Sql & "FROM T_Clients "
Sql = Sql & "ORDER BY T_Clients.Client;"
MyControl.AddItem ""
Set Rs = Con.OpenRecordSet(Sql)
While Rs.EOF = False
    MyControl.AddItem Trim("" & Rs!Client)
        If MyControl.ListCount = 1 Then MyControl.Text = Trim("" & Rs!Client)

    Rs.MoveNext
Wend
Set Rs = Con.CloseRecordSet(Rs)
Con.CloseConnection
End Sub
Public Function ChercheXls(Myrange, Val) As Long
ChercheXls = 0
 For i = 2 To Myrange.Rows.Count
                If UCase(Trim("" & Myrange(i))) = UCase(Trim("" & Val)) Then
                        ChercheXls = i
                        Exit For
                End If
            Next i



End Function
Public Function CherCheInFihier(Cherher As String) As String
Dim FileNumber As Long
Dim MyString As String
FileNumber = FreeFile
  Set AutoApp = ThisDrawing.Application

Open AutoApp.ActiveDocument.Path & "\Autocable.ini" For Input As #FileNumber
Do While Not EOF(FileNumber)    ' Effectue la boucle jusqu'à la fin du fichier.
    Input #FileNumber, MyString ' Lit les données dans deux variables.
    If InStr(1, MyString, Cherher) <> 0 Then
       CherCheInFihier = Right(MyString, Len(MyString) - (Len(Cherher) + InStr(1, MyString, Cherher)))
       Exit Do
    End If
Loop
Close #FileNumber    ' Ferme le fichier
CherCheInFihier = Replace(CherCheInFihier, "§remplaceDate§", Format(Date, "yyyy"))
End Function
Public Function RenseigneConnecteurBroches(RangeAttribue As Recordset) As Boolean
Dim txtErr As String
    On Error Resume Next
    RenseigneConnecteurBroches = False
    'If ("" & RangeAttribue.Fields("APP") = "107AB") Or ("" & RangeAttribue.Fields("APP2") = "107AB") Then
    'MsgBox ""
    'End If
    If TableauDeConnecteurs(CLng(CollectionCon("" & RangeAttribue.Fields("APP")))).ConnecteurExiste = True Then
        If TableauDeConnecteurs(CLng(CollectionCon("" & RangeAttribue.Fields("APP")))).EPISSURE = False Then
            a = TableauDeConnecteurs(CLng(CollectionCon("" & RangeAttribue.Fields("APP")))).NewBlock.GetAttributes
            txtErr = "LIAI"
            IdAttrib = TableauDeConnecteurs(CLng(CollectionCon("" & RangeAttribue.Fields("APP")))).Attribues.Item("LIAI" & RangeAttribue.Fields(9))
            If Err Then
                FunError 5, txtErr & RangeAttribue.Fields(9), Err.Description, "" & RangeAttribue.Fields("APP")
                Err.Clear
            End If
            dd = TableauDeConnecteurs(CLng(CollectionCon("" & RangeAttribue.Fields("APP")))).Attribues.Count
            a(IdAttrib).TextString = "" & RangeAttribue.Fields(0)
             txtErr = "FIL"
            IdAttrib = TableauDeConnecteurs(CLng(CollectionCon("" & RangeAttribue.Fields("APP")))).Attribues.Item("FIL" & RangeAttribue.Fields(9))
            If Trim("" & a(IdAttrib).TextString) <> "" Then
                 txtErr = "MAR"
                IdAttrib = TableauDeConnecteurs(CLng(CollectionCon("" & RangeAttribue.Fields("APP")))).Attribues.Item("MAR" & RangeAttribue.Fields(9))
            End If
            a(IdAttrib).TextString = "" & RangeAttribue.Fields(2)
        Else
            If FunEPISSURE(TableauDeConnecteurs(CLng(CollectionCon("" & RangeAttribue.Fields("APP")))).NewBlock.GetAttributes, "" & RangeAttribue.Fields(2), "" & RangeAttribue.Fields(9), CLng(CollectionCon("" & RangeAttribue.Fields("APP")))) = False Then Exit Function
        End If

    Else
        FunError 3, "" & RangeAttribue.Fields(2), Err.Description, "" & RangeAttribue.Fields("APP")
    End If
    If TableauDeConnecteurs(CLng(CollectionCon("" & RangeAttribue.Fields("APP2")))).ConnecteurExiste = True Then

        If TableauDeConnecteurs(CLng(CollectionCon("" & RangeAttribue.Fields("APP2")))).EPISSURE = False Then
            a = TableauDeConnecteurs(CLng(CollectionCon("" & RangeAttribue.Fields("APP2")))).NewBlock.GetAttributes
             txtErr = "LIAI"
            IdAttrib = TableauDeConnecteurs(CLng(CollectionCon("" & RangeAttribue.Fields("APP2")))).Attribues.Item("LIAI" & RangeAttribue.Fields(12))
            If Err Then
                FunError 5, txtErr & RangeAttribue.Fields(12), Err.Description, "" & RangeAttribue.Fields("APP2")
                Err.Clear
            End If
        
            dd = TableauDeConnecteurs(CLng(CollectionCon("" & RangeAttribue.Fields("APP2")))).Attribues.Count
            a(IdAttrib).TextString = "" & RangeAttribue.Fields(0)
             txtErr = "FIL"
            IdAttrib = TableauDeConnecteurs(CLng(CollectionCon("" & RangeAttribue.Fields("APP2")))).Attribues.Item("FIL" & RangeAttribue.Fields(12))
            If Trim("" & a(IdAttrib).TextString) <> "" Then
             txtErr = "MAR"
                IdAttrib = TableauDeConnecteurs(CLng(CollectionCon("" & RangeAttribue.Fields("APP2")))).Attribues.Item("MAR" & RangeAttribue.Fields(12))
            End If
            a(IdAttrib).TextString = "" & RangeAttribue.Fields(2)
        Else
            If FunEPISSURE(TableauDeConnecteurs(CLng(CollectionCon("" & RangeAttribue.Fields("APP2")))).NewBlock.GetAttributes, "" & RangeAttribue.Fields(2), "" & RangeAttribue.Fields(12), CLng(CollectionCon("" & RangeAttribue.Fields("APP2")))) = False Then Exit Function

        End If
    Else
        FunError 3, "" & RangeAttribue.Fields(2), Err.Description, "" & RangeAttribue.Fields("APP2")
    End If
    RenseigneConnecteurBroches = True
End Function
Sub AttribueLibV(NewBlock As AcadBlockReference, Index As Long)
    Dim At
    Dim MyAtt As New Collection
    At = NewBlock.GetAttributes
    
    For i = 0 To UBound(At)
        DoEvents
       
        Debug.Print At(i).TagString
        MyAtt.Add CStr(i), At(i).TagString
    Next i
    Set TableauDeConnecteurs(Index).AttribuesFils = MyAtt
    Ats = TableauDeConnecteurs(Index).NewBlock.GetAttributes
    At(TableauDeConnecteurs(Index).AttribuesFils("DESIGNATION")).TextString = Ats(TableauDeConnecteurs(Index).Attribues("DESIGNATION")).TextString & " (" & Ats(TableauDeConnecteurs(Index).Attribues("N°")).TextString & ")"
    Set MyAtt = Nothing
    i3 = UBound(At) - 1
    Dim i2 As Long
    For i2 = 0 To i3
        Debug.Print At(i2).TagString
    Next i2
    For i = 1 To TableauDeConnecteurs(Index).indexFile
        DoEvents
       
        At(TableauDeConnecteurs(Index).AttribuesFils("FIL" & CStr(i))).TextString = TableauDeConnecteurs(Index).TableauFile(i)
    Next i
End Sub
Sub TestFl()
a = CherCheInFihier("Bdnumero")
End Sub
Public Function LoadConnecteur(IdIndiceProjet As Long) As Boolean
    LoadConnecteur = False
    Dim RsConnecteur As Recordset
    Dim Sql As String
    Dim MyRep As String
    Dim Trouve As Boolean
   Dim NbCol  As Long
    Dim NbConnecteur As Long
    Dim fso As New FileSystemObject
    Dim NumErr As Long
    Dim Nb_L_C As Long
'    Set CollectionCon = Nothing
'    Set CollectionCon = New Collection
    
    Sql = "SELECT T_indiceProjet.Client FROM T_indiceProjet "
    Sql = Sql & "WHERE T_indiceProjet.Id=" & IdIndiceProjet & ";"

    NumErr = 1

    Set RsConnecteur = Con.OpenRecordSet(Sql)
    LeCient = UCase(Trim("" & RsConnecteur!Client))
Select Case UCase(Trim("" & RsConnecteur!Client))
    Case "RENAULT"
        boolFormClient = True
        MyCARTOUCHE_Client = "RENAULT"
    Case Else
        
         MyCARTOUCHE_Client = "RENAULT"
End Select

 Sql = "SELECT Connecteurs.CONNECTEUR, Connecteurs.[O/N],  "
Sql = Sql & "Connecteurs.DESIGNATION, Connecteurs.CODE_APP,  "
Sql = Sql & "Connecteurs.N°, Connecteurs.POS, Connecteurs.PRECO1,  "
Sql = Sql & "Connecteurs.PRECO2  "
Sql = Sql & "FROM Connecteurs "
Sql = Sql & "WHERE Connecteurs.Id_IndiceProjet=" & IdIndiceProjet & " "
    Sql = Sql & "ORDER BY Connecteurs.N°;"
    NumErr = 1

    Set RsConnecteur = Con.OpenRecordSet(Sql)
    InsertPointLigneTableau_Vignette(0) = -1146.1429: InsertPointLigneTableau_Vignette(1) = 870.4179: InsertPointLigneTableau_Vignette(2) = 0
    For i = 0 To IndexIstC
    InsertPointConnecteur(i).InsertPointConnecteur(0) = 30 + (150 * i): InsertPointConnecteur(i).InsertPointConnecteur(1) = 870.4179 + (150 * i): InsertPointConnecteur(i).InsertPointConnecteur(2) = 0
    Next i
    i = 1
      NbConnecteur = 0
    For i = 1 To CollectionCon.Count
      If NbConnecteur < CollectionCon(i) Then
        NbConnecteur = CollectionCon(i)
      End If
    Next i
    i = 1
    While "" & RsConnecteur.EOF = False
   
    If Trim(UCase("" & RsConnecteur.Fields(0))) <> "NEANT" Then
   
        On Error Resume Next
        NbCol = CLng(CollectionCon("" & RsConnecteur.Fields(3)))
        If Err Then
            Err.Clear
            
           NbConnecteur = NbConnecteur + 1
                CollectionCon.Add NbConnecteur, Trim("" & RsConnecteur.Fields(3))
            
        End If
         
         On Error GoTo 0
     Else
        NbConnecteur = NbConnecteur + 1
     End If
     
  
       RsConnecteur.MoveNext
    Wend
  
    
    ReDim Preserve TableauDeConnecteurs(NbConnecteur)
     FormBarGrah.ProgressBar1.Value = 0
    If NbConnecteur = 0 Then
     FormBarGrah.ProgressBar1.Max = 1 + 1
    Else
         FormBarGrah.ProgressBar1.Max = 1 + NbConnecteur
    End If
     FormBarGrah.ProgressBar1Caption.Caption = "Chargement des connecteurs"
    If NbConnecteur <> 0 Then
        RsConnecteur.MoveFirst
    End If
      On Error GoTo GesERR
    While RsConnecteur.EOF = False
         FormBarGrah.ProgressBar1.Value = FormBarGrah.ProgressBar1.Value + 1
        DoEvents
        
        DoEvents


        If UCase("" & RsConnecteur.Fields(0)) <> "NEANT" Then
            If fso.FileExists(TableauPath.Item("PathConnecteurs" & LeCient) & "" & RsConnecteur.Fields(0) & ".dwg") = True Then
                MyRep = TableauPath.Item("PathConnecteurs" & LeCient)
                Trouve = True
                NumErr = 4
              
                
                TableauDeConnecteurs(CLng(CollectionCon("" & RsConnecteur.Fields(3)))).ConnecteurExiste = True
            Else
                NumErr = 1
                TableauDeConnecteurs(CLng(CollectionCon("" & RsConnecteur.Fields(3)))).ConnecteurExiste = False
                MyRep = ""
                
GesERR:
                Trouve = False
                FunError NumErr, "" & RsConnecteur.Fields(3), Err.Description, "" & RsConnecteur.Fields(0)
            End If
            If Trouve = True Then
            If TableauDeConnecteurs(CLng(CollectionCon("" & RsConnecteur.Fields(3)))).PosOk = True Then
                Set TableauDeConnecteurs(CLng(CollectionCon("" & RsConnecteur.Fields(3)))).NewBlock = FunInsBlock(MyRep & "" & RsConnecteur.Fields(0) & ".dwg", TableauDeConnecteurs(CLng(CollectionCon("" & RsConnecteur.Fields(3)))).InsertPointLigneC, "", TableauDeConnecteurs(CLng(CollectionCon("" & RsConnecteur.Fields(3)))).RotationC, TableauDeConnecteurs(CLng(CollectionCon("" & RsConnecteur.Fields(3)))).XScaleFactorC, TableauDeConnecteurs(CLng(CollectionCon("" & RsConnecteur.Fields(3)))).YScaleFactorC, TableauDeConnecteurs(CLng(CollectionCon("" & RsConnecteur.Fields(3)))).ZScaleFactorC)
            Else
                Set TableauDeConnecteurs(CLng(CollectionCon("" & RsConnecteur.Fields(3)))).NewBlock = FunInsBlock(MyRep & "" & RsConnecteur.Fields(0) & ".dwg", InsertPointConnecteur(Nb_L_C).InsertPointConnecteur, "")
                InsertPointConnecteur(Nb_L_C).InsertPointConnecteur(0) = DecalInsertPointLigneTableau_fils_Gauche(InsertPointConnecteur(Nb_L_C).InsertPointConnecteur(0), 300)
                Nb_L_C = Nb_L_C + 1
                If Nb_L_C = IndexIstC + 1 Then Nb_L_C = 0
             End If
                  If ErrInsert = True Then GoTo EnrSuinant
                If UCase("" & RsConnecteur.Fields(1)) = "O" Then
                    TableauDeConnecteurs(CLng(CollectionCon("" & RsConnecteur.Fields(3)))).EPISSURE = True
                    If TableauDeConnecteurs(CLng(CollectionCon("" & RsConnecteur.Fields(3)))).PosOk = True Then

                    Set TableauDeConnecteurs(CLng(CollectionCon("" & RsConnecteur.Fields(3)))).NewVignette = FunInsBlock(MyRep & "EPISSURES.dwg", TableauDeConnecteurs(CLng(CollectionCon("" & RsConnecteur.Fields(3)))).InsertPointLigneV, "V" & "" & RsConnecteur.Fields(4), TableauDeConnecteurs(CLng(CollectionCon("" & RsConnecteur.Fields(3)))).RotationV, TableauDeConnecteurs(CLng(CollectionCon("" & RsConnecteur.Fields(3)))).XScaleFactorV, TableauDeConnecteurs(CLng(CollectionCon("" & RsConnecteur.Fields(3)))).YScaleFactorV, TableauDeConnecteurs(CLng(CollectionCon("" & RsConnecteur.Fields(3)))).ZScaleFactorV)
                    Else
                        Set TableauDeConnecteurs(CLng(CollectionCon("" & RsConnecteur.Fields(3)))).NewVignette = FunInsBlock(MyRep & "EPISSURES.dwg", InsertPointLigneTableau_Vignette, "V" & "" & RsConnecteur.Fields(4))

                        InsertPointLigneTableau_Vignette(0) = DecalInsertPointLigneTableau_fils_Gauche(InsertPointLigneTableau_Vignette(0), 80)
                        NbLignesVignette = NbLignesVignette + 1
                    End If
                Else
                    TableauDeConnecteurs(CLng(CollectionCon("" & RsConnecteur.Fields(3)))).EPISSURE = False
                    If TableauDeConnecteurs(CLng(CollectionCon("" & RsConnecteur.Fields(3)))).PosOk = True Then

                    Set TableauDeConnecteurs(CLng(CollectionCon("" & RsConnecteur.Fields(3)))).NewVignette = FunInsBlock(MyRep & "VIGNETTE CONNECTEUR.dwg", TableauDeConnecteurs(CLng(CollectionCon("" & RsConnecteur.Fields(3)))).InsertPointLigneV, "V" & "" & RsConnecteur.Fields(4), TableauDeConnecteurs(CLng(CollectionCon("" & RsConnecteur.Fields(3)))).RotationV, TableauDeConnecteurs(CLng(CollectionCon("" & RsConnecteur.Fields(3)))).XScaleFactorV, TableauDeConnecteurs(CLng(CollectionCon("" & RsConnecteur.Fields(3)))).YScaleFactorV, TableauDeConnecteurs(CLng(CollectionCon("" & RsConnecteur.Fields(3)))).ZScaleFactorV)
                    Else
                    Set TableauDeConnecteurs(CLng(CollectionCon("" & RsConnecteur.Fields(3)))).NewVignette = FunInsBlock(MyRep & "VIGNETTE CONNECTEUR.dwg", InsertPointLigneTableau_Vignette, "V" & "" & RsConnecteur.Fields(4))

                    InsertPointLigneTableau_Vignette(0) = DecalInsertPointLigneTableau_fils_Gauche(InsertPointLigneTableau_Vignette(0), 80)
                    NbLignesVignette = NbLignesVignette + 1
                    End If
                End If
                Set TableauDeConnecteurs(CLng(CollectionCon("" & RsConnecteur.Fields(3)))).Attribues = ColectionAttribueConecteur(TableauDeConnecteurs(CLng(CollectionCon("" & RsConnecteur.Fields(3)))).NewBlock.GetAttributes)
                Set TableauDeConnecteurs(CLng(CollectionCon("" & RsConnecteur.Fields(3)))).AttribuesVignette = ColectionAttribueConecteur(TableauDeConnecteurs(CLng(CollectionCon("" & RsConnecteur.Fields(3)))).NewVignette.GetAttributes)

                At = TableauAtribCon(RsConnecteur, TableauDeConnecteurs(CLng(CollectionCon("" & RsConnecteur.Fields(3)))).EPISSURE)
                funAttributesLigne_Tableau_fils TableauDeConnecteurs(CLng(CollectionCon("" & RsConnecteur.Fields(3)))).NewBlock.Name, TableauDeConnecteurs(CLng(CollectionCon("" & RsConnecteur.Fields(3)))).NewBlock.GetAttributes, At, "" & RsConnecteur.Fields.Count - 1, RsConnecteur, True, TableauDeConnecteurs(CLng(CollectionCon("" & RsConnecteur.Fields(3)))).Attribues
                funAttributesLigne_Tableau_fils TableauDeConnecteurs(CLng(CollectionCon("" & RsConnecteur.Fields(3)))).NewVignette.Name, TableauDeConnecteurs(CLng(CollectionCon("" & RsConnecteur.Fields(3)))).NewVignette.GetAttributes, At, "" & RsConnecteur.Fields.Count - 1, RsConnecteur, True, TableauDeConnecteurs(CLng(CollectionCon("" & RsConnecteur.Fields(3)))).AttribuesVignette, True, TableauDeConnecteurs(CLng(CollectionCon("" & RsConnecteur.Fields(3)))).EPISSURE
                
            End If
        End If
        If NbLignesVignette = 14 Then
            InsertPointLigneTableau_Vignette(0) = -1146.1429
            InsertPointLigneTableau_Vignette(1) = DecalInsertPointLigneTableau_fils_Bas(InsertPointLigneTableau_Vignette(1), -40)
            NbLignesVignette = 0
        End If
EnrSuinant:
       RsConnecteur.MoveNext
        i = i + 1
    Wend
    LoadConnecteur = True
    Set fso = Nothing
End Function


Public Function PRECO(Var As String, Optional Iis As Boolean) As String
PRECO = Var
PRECO = Replace(UCase(PRECO), "CODE.APP", "CODE_APP")

If InStr(1, UCase(PRECO), "PRECO") <> 0 Then
    PRECO = "PRECO" & Right(PRECO, 1)
    
End If
If Iis = True Then

If (InStr(1, UCase(Var), "PRECO") <> 0) And (InStr(1, UCase(Var), "1") <> 0) Then
    PRECO = "PRECO1"
    
End If
If (InStr(1, UCase(Var), "PRECO") <> 0) And (InStr(1, UCase(Var), "2") <> 0) Then
    PRECO = "PRECO2"
    
End If
    If InStr(1, UCase(PRECO), "FIL") <> 0 Then
        PRECO = "FIL"
    
    End If
    
    If InStr(1, UCase(Var), "_FILS") <> 0 Then
        PRECO = "_FILS"
        
    End If
End If
End Function

Public Function DecodeCode_APP(Code_APP As String) As String
Dim SplitCode_APP
Dim NbUbound As Long
SlitCode_APP = Split(Code_APP, "_")
NbUbound = UBound(SlitCode_APP)
Select Case NbUbound
Case -1
    DecodeCode_APP = vbNullChar
Case 0
    DecodeCode_APP = SlitCode_APP(0)
Case 1
    DecodeCode_APP = SlitCode_APP(0)
Case 2
    DecodeCode_APP = SlitCode_APP(1)
Case Else
     DecodeCode_APP = SlitCode_APP(1)
    End Select
End Function
Sub test()
a = DecodeCode_APP("exzf_120_aa_ee")

a = DecodeCode_APP("exzf_120_aa")
a = DecodeCode_APP("120_aa")
a = DecodeCode_APP("120")
a = DecodeCode_APP("")

End Sub

Attribute VB_Name = "Module1"
Sub LireRep()
Dim fso As New FileSystemObject
Dim rep
Dim MyExcel As New Excel.Application
Dim MyWorkbook As Excel.Workbook
Dim MyWorksheet As Excel.Worksheet
Set MyWorkbook = MyExcel.Workbooks.Add
Set MyWorksheet = MyWorkbook.Sheets.Add
Dim Myrange As Excel.Range
MyExcel.Visible = True
i = 0
'MyWorksheet.Cells(i, 1) = "Fichiers"
'MyWorksheet.Cells(i, 2) = "Date"

 rep = Dir("\\Enc-srv-prod-01\donnees d entreprise\Utilitaires\cablage\Librairies\Connecteurs\*.*")
 While rep <> ""

 If InStr(1, UCase(rep), ".DWG") <> 0 Then
 i = i + 1
 MyWorksheet.Cells(i, 1) = "\\Enc-srv-prod-01\donnees d entreprise\Utilitaires\cablage\Librairies\Connecteurs\" & rep
  MyWorksheet.Cells(i, 2) = fso.GetFile("\\Enc-srv-prod-01\donnees d entreprise\Utilitaires\cablage\Librairies\Connecteurs\" & rep).DateLastModified
 End If
 rep = Dir
 Wend
  rep = Dir("\\Enc-srv-prod-01\donnees d entreprise\Utilitaires\cablage\Librairies\Connecteurs\Construction connecteurs\*.*")
 While rep <> ""

 If InStr(1, UCase(rep), ".DWG") <> 0 Then
 i = i + 1
 MyWorksheet.Cells(i, 1) = "\\Enc-srv-prod-01\donnees d entreprise\Utilitaires\cablage\Librairies\Connecteurs\Construction connecteurs\" & rep
  MyWorksheet.Cells(i, 2) = fso.GetFile("\\Enc-srv-prod-01\donnees d entreprise\Utilitaires\cablage\Librairies\Connecteurs\Construction connecteurs\" & rep).DateLastModified
 End If
 rep = Dir
 Wend
 Set Myrange = MyWorksheet.Range("a1").CurrentRegion
    Myrange.Sort Key1:=Range("B1"), Order1:=xlAscending, Header:= _
        xlGuess, OrderCustom:=1, MatchCase:=False, Orientation:=xlTopToBottom, _
        DataOption1:=xlSortNormal
        
        For i = 1 To Myrange.Rows.Count
            rep = Dir(Myrange(i, 1))
            If fso.FileExists("\\Enc-srv-prod-01\donnees d entreprise\Utilitaires\cablage\Librairies\Blocs de construction\ConecteurXls\" & rep) = True Then
                fso.DeleteFile "\\Enc-srv-prod-01\donnees d entreprise\Utilitaires\cablage\Librairies\Blocs de construction\ConecteurXls\" & rep
            End If
         fso.CopyFile Myrange(i, 1), "\\Enc-srv-prod-01\donnees d entreprise\Utilitaires\cablage\Librairies\Blocs de construction\ConecteurXls\" & rep
         DoEvents
        Next i
        ChargeConecteur Myrange
'
End Sub
Sub ChargeConecteur(Myrange As Range)
    Dim MyRep
    Dim Block As AcadBlockReference
     Set AutoApp = ThisDrawing.Application
     AutoApp.Documents.Add
      rep = Dir("\\Enc-srv-prod-01\donnees d entreprise\Utilitaires\cablage\Librairies\Blocs de construction\ConecteurXls\*.*")
      InsertPointLigneTableau_fils(0) = 1
      InsertPointLigneTableau_fils(1) = 1
      InsertPointLigneTableau_fils(2) = 1
       While rep <> ""
            
           Set Block = FunInsBlock("\\Enc-srv-prod-01\donnees d entreprise\Utilitaires\cablage\Librairies\Blocs de construction\ConecteurXls\" & rep, InsertPointLigneTableau_fils)
            rep = Dir
         DoEvents
       whend
End Sub

Attribute VB_Name = "VariableGlobales"
Public AutoApp As AcadApplication
Public InsertPointLigneTableau_fils(0 To 2) As Double
Public InsertPointLigneTableau_Vignette(0 To 2) As Double
Public MyEcel As Excel.Application
Public TableauPath As New Collection
Public NbContolClient As Long
Public boolExec As Boolean
Dim NewBlock  As AcadBlockReference
Public Admin As Boolean
Public Lecture As Boolean
Public Ecriture As Boolean
Public Creation As Boolean
Public Loguer As Boolean
Public NoClose As Boolean
Public boolQuitte As Boolean
Public ActifDoc As String
Public DbNumPlan As String
Public db As String
Public varProjet As String
Public varIndice As String
Public Con As New Ado
Public ConNumPlan As New Ado
Public MyCARTOUCHE_Client
Public LeCartouche As String
Public LeCartoucheE As String
Public AttribuCartouche As New Collection
Public JobError As Long
Public Fichier As String
Public NbLignesVignette As Long
Public ErrInsert As Boolean
Public boolFormClient As Boolean
Public MenuShow As Boolean
Type T_Con
    Kill As Boolean
    NewBlock  As AcadBlockReference
    Attribues As Collection
    NewVignette  As AcadBlockReference
    AttribuesVignette As Collection
    EPISSURE As Boolean
    indexFile As Long
    TableauFile() As String
    AttribuesFils As Collection
    ConnecteurExiste As Boolean
    InsertPointLigneC(0 To 2) As Double
    InsertPointLigneV(0 To 2) As Double
    InsertPointLigneE(0 To 2) As Double
    XScaleFactorC As Double
    YScaleFactorC As Double
    ZScaleFactorC As Double
    XScaleFactorV As Double
    YScaleFactorV As Double
    ZScaleFactorV As Double
    RotationC As Double
    RotationV As Double
    PosOk As Boolean
End Type
Type PointConnecteur
    InsertPointConnecteur(0 To 2) As Double
End Type
Public Const IndexIstC = 9
Public InsertPointConnecteur(0 To IndexIstC) As PointConnecteur

Public TableauDeConnecteurs() As T_Con
Public LeCient As String
Public VarPreced As Boolean
Public boolCreationPlan As Boolean
Public CollectionCon As Collection
Public NbError As Long
Public FormBarGrah As Object
