Attribute VB_Name = "FunCreateObjet"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Public Function CrateCercle(MyDocumment, InsertPoint, Rayon As Double, Couleur As Long)
Set CrateCercle = MyDocumment.ModelSpace.AddCircle(InsertPoint, Rayon)
CrateCercle.Color = Couleur
End Function
Public Function CrateCadre(MyDocumment, InsertPointCadre, Couleur As Long)
  Dim points(0 To 14) As Double
    
 
    points(0) = InsertPointCadre(0): points(1) = InsertPointCadre(1): points(2) = 0
    points(3) = InsertPointCadre(2): points(4) = InsertPointCadre(1): points(5) = 0
    points(6) = InsertPointCadre(2): points(7) = InsertPointCadre(3): points(8) = 0
    points(9) = InsertPointCadre(0): points(10) = InsertPointCadre(3): points(11) = 0
    points(12) = InsertPointCadre(0): points(13) = InsertPointCadre(1): points(14) = 0
    Set CrateCadre = MyDocumment.ModelSpace.AddPolyline(points)

CrateCadre.Color = Couleur
End Function

Public Function DefinirEspace(Y As Double, x As Double, NbLigne As Double, NbColonne As Double, OfsetX As Double, OfsetY As Double, Crecle As Boolean)
Dim MyCadre(3) As Double
MyCadre(0) = OfsetX
MyCadre(1) = OfsetY
If Crecle = False Then
    MyCadre(2) = OfsetX + (x * NbColonne)
Else
    MyCadre(2) = OfsetX + (Y * NbColonne)
End If
MyCadre(3) = OfsetY + (Y * NbLigne)


DefinirEspace = MyCadre
End Function
Public Function CreateLigne(MyDocumment, XY1, XY2, Couleur As Long)
    Set CreateLigne = MyDocumment.ModelSpace.AddLine(XY1, XY2)
    CreateLigne.Color = Couleur
    MyDocumment.Application.ZoomAll
End Function
Public Function CreateEtiquette(MyDocumment, txt As String, XY1, Couleur As Long, Alignment, Optional Rotation = 0)
    Set CreateEtiquette = MyDocumment.ModelSpace.AddText(txt, XY1, 3)
    CreateEtiquette.Alignment = Alignment
    If Alignment <> 0 Then CreateEtiquette.TextAlignmentPoint = XY1
    CreateEtiquette.Rotation = Rotation
    CreateEtiquette.Color = Couleur
End Function
Public Function CreateEtiquetteM(MyDocumment, txt As String, XY1, Couleur As Long, AttachmentPoint, Optional Rotation = 0)
    Set CreateEtiquetteM = MyDocumment.ModelSpace.AddMText(XY1, 3, txt)
    CreateEtiquetteM.AttachmentPoint = AttachmentPoint
    CreateEtiquetteM.Rotation = Rotation
'acAttachmentPointMiddleCenter
    CreateEtiquetteM.TextAlignmentPoint = XY1
    CreateEtiquetteM.Color = Couleur
End Function


Public Function CreateAttribue(MyDocumment, Prompt As String, txt As String, Defaulttxt As String, XY1, Couleur As Long, Alignment, Optional Rotation = 0)
    Set CreateAttribue = MyDocumment.ModelSpace.AddAttribute(3, acAttributeModeNormal, Prompt, XY1, txt, Defaulttxt)
    CreateAttribue.Alignment = Alignment
    CreateAttribue.Rotation = Rotation
    If Alignment <> 0 Then _
    CreateAttribue.TextAlignmentPoint = XY1
    CreateAttribue.Color = Couleur
End Function

Public Sub SelectCopy(Documen1, Document2, x As Double, Y As Double, index)
Dim InserCadre(4)
Dim XY1(0 To 2) As Double
Dim XY2(0 To 2) As Double
 Dim InseterPoint
  For i = 0 To Documen1.ModelSpace.Count - 1
  Documen1.ModelSpace(i).Activate
' CreateLigne ThisDrawing , ThisDrawing.ModelSpace(i).Select
  Set aa = Documen1.ModelSpace(i)
 Debug.Print aa.ObjectName
 aa.Copy
 Document2.paste
Select Case aa.ObjectName
        Case "AcDbLine"
            InseterPoint = aa.StartPoint
            XY1(0) = InseterPoint(0) + x
            XY1(1) = InseterPoint(1) + Y
             InseterPoint = aa.EndPoint
            XY2(0) = InseterPoint(0) + x
            XY2(1) = InseterPoint(1) + Y
            CreateLigne Document2, XY1, XY2, aa.Color
        Case "AcDbAttributeDefinition"
            InseterPoint = aa.InsertionPoint
            InseterPoint(0) = InseterPoint(0) + x
            InseterPoint(1) = InseterPoint(1) + Y
            CreateAttribue Document2, aa.PromptString, Replace(UCase(aa.TagString), UCase("[RNum]"), index), aa.TextString, InseterPoint, aa.Color, aa.Alignment, aa.Rotation
          Case "AcDbPolyline"
         
          InseterPoint = aa.Coordinates
          InserCadre(0) = InseterPoint(4) + x
           InserCadre(1) = InseterPoint(5) + Y
            InserCadre(2) = InseterPoint(0) + x
             InserCadre(3) = InseterPoint(1) + Y
             CrateCadre Document2, InserCadre, aa.Color
          Case "AcDbCircle"
            InseterPoint = aa.Center
            InseterPoint(0) = InseterPoint(0) + x
            InseterPoint(1) = InseterPoint(1) + Y
            CrateCercle Document2, InseterPoint, aa.Radius, aa.Color
          Case "AcDbMText"
           InseterPoint = aa.InsertionPoint
            InseterPoint(0) = InseterPoint(0) + x
            InseterPoint(1) = InseterPoint(1) + Y
          CreateEtiquetteM Document2, Replace(aa.TextString, "[RNum]", index), InseterPoint, aa.Color, aa.AttachmentPoint, aa.Rotation
        Case "AcDbText"
           InseterPoint = aa.InsertionPoint
            InseterPoint(0) = InseterPoint(0) + x
            InseterPoint(1) = InseterPoint(1) + Y
          CreateEtiquette Document2, Replace(aa.TextString, "[RNum]", index), InseterPoint, aa.Color, aa.Alignment, aa.Rotation
End Select
'    ThisDrawing.Activate
    
  Next
 
End Sub
Public Function CovertNumChar(Num As Long) As String
Dim txt As String

txt = "A"
Dim NumCal As Long

For i = 0 To Num - 1
    NumCal = Len(txt)
    If i > 0 Then
        Mid(txt, NumCal, 1) = Chr(Asc(Mid(txt, NumCal, 1)) + 1)
    End If
    Debug.Print Asc(Mid(txt, NumCal, 1))
    If Asc(Mid(txt, NumCal, 1)) = 91 Then
        Mid(txt, NumCal, 1) = Chr(97)
    End If
    If Asc(Mid(txt, NumCal, 1)) = 123 Then
       
            Mid(txt, NumCal, 1) = "A"
            NumCal = NumCal - 1
    End If
    If NumCal = 0 Then
        txt = txt & "A"
    End If
Next
CovertNumChar = txt
End Function

Attribute VB_Name = "Module1"
Function NewRealai(OfsetX As Double, OfsetY As Double, MyType As String, Cercle As Boolean)
    Dim CadreX As Double
Dim CadreY As Double
Dim MyFBloc As New FunCreateObjet
Dim a(0 To 2) As Double
 
Dim MyPos
Dim XY1(0 To 2) As Double
Dim XY2(0 To 2) As Double
Dim NbL As Double
Dim NbC As Double




NbL = 1
NbC = 1

'MyFBloc.SelectCopy ThisDrawing, ThisDrawing, 100, 10
a(0) = 10
a(1) = 10
a(2) = 1
 CadreX = 67
 CadreY = 67
'Set MyCercle = MyFBloc.CrateCercle(a, 10, acByBlock)
'Set MyCercle = MyFBloc.CrateCadre(MyFBloc.DefinirEspace(20, 3, 10, 36, 0))
MyPos = MyFBloc.DefinirEspace(CadreY + 8, CadreX + 8, NbL, NbC, OfsetX, OfsetY, Cercle)
'a(0) = MyPos(1) + 10
'a(1) = MyPos(3) - 10
a(0) = MyPos(0) + 5
a(1) = MyPos(3) - 20
a(2) = 1
Cv = a(0)
Lv = a(1)
Dim i As Long
For l = 1 To NbL
DoEvents
    a(0) = Cv
    For c = 1 To NbC
    i = i + 1
  Set aa = Application.Documents("Relai1.dwg").SendCommand("_COPYCLIP ")
 
    MyFBloc.SelectCopy Application.Documents("Relai1.dwg"), Application.Documents("ModelBloc.dwg"), a(0), a(1), i
Next
Next

End Function

Function NewConnecteur(OfsetX As Double, OfsetY As Double, MyType As String, Cercle As Boolean)
'For i = 0 To ThisDrawing.ModelSpace.Count - 1
'Debug.Print ThisDrawing.ModelSpace(i).ObjectName
'
'Next

Dim CadreX As Double
Dim CadreY As Double
Dim MyFBloc As New FunCreateObjet
Dim a(0 To 2) As Double
 
Dim MyPos
Dim XY1(0 To 2) As Double
Dim XY2(0 To 2) As Double
Dim NbL As Double
Dim NbC As Double




NbL = 10
NbC = 10

'MyFBloc.SelectCopy ThisDrawing, ThisDrawing, 100, 10
a(0) = 10
a(1) = 10
a(2) = 1
 CadreX = 13
 CadreY = 20
'Set MyCercle = MyFBloc.CrateCercle(a, 10, acByBlock)
'Set MyCercle = MyFBloc.CrateCadre(MyFBloc.DefinirEspace(20, 3, 10, 36, 0))
MyPos = MyFBloc.DefinirEspace(CadreY + 8, CadreX + 8, NbL, NbC, OfsetX, OfsetY, Cercle)
'a(0) = MyPos(1) + 10
'a(1) = MyPos(3) - 10
a(0) = MyPos(0) + 5
a(1) = MyPos(3) - 20
a(2) = 1
Cv = a(0)
Lv = a(1)
Dim i As Long
For l = 1 To NbL
DoEvents
    a(0) = Cv
    For c = 1 To NbC
    i = i + 1
    
'Ligne Colone



Select Case UCase(MyType)

'        1,2,3...
        Case "1"
                CreatAlveole ThisDrawing, MyFBloc.DefinirEspace(1, 1, CadreY, CadreX, a(0), a(1) - (4 * l), Cercle), acByBlock, _
                "TOTO :", "toto", "12345678", CadreY, CadreX, MyFBloc, Val(i), Cercle
                
'        10,9,8..
        Case "10"
                CreatAlveole ThisDrawing, MyFBloc.DefinirEspace(1, 1, CadreY, CadreX, a(0), a(1) - (4 * l), Cercle), acByBlock, _
                "TOTO :", "toto", "12345678", CadreY, CadreX, MyFBloc, ((NbC * NbL) + 1) - i, Cercle
                
'        1-1,1-2,1-3...
         Case "11"
            CreatAlveole ThisDrawing, MyFBloc.DefinirEspace(1, 1, CadreY, CadreX, a(0), a(1) - (4 * l), Cercle), acByBlock, _
                    "TOTO :", "toto", "12345678", CadreY, CadreX, MyFBloc, Val(l) & "-" & Val(c), Cercle
                    
'        10-1,10-2,10-3...
        Case "101"
            CreatAlveole ThisDrawing, MyFBloc.DefinirEspace(1, 1, CadreY, CadreX, a(0), a(1) - (4 * l), Cercle), acByBlock, _
                    "TOTO :", "toto", "12345678", CadreY, CadreX, MyFBloc, NbL + 1 - Val(l) & "-" & Val(c), Cercle
                    
'        1-10,1-9,1-8...
        Case "110"
            CreatAlveole ThisDrawing, MyFBloc.DefinirEspace(1, 1, CadreY, CadreX, a(0), a(1) - (4 * l), Cercle), acByBlock, _
                    "TOTO :", "toto", "12345678", CadreY, CadreX, MyFBloc, Val(l) & "-" & NbC + 1 - Val(c), Cercle
                    
'        10-10,10-9,10-8...
        Case "1010"
            CreatAlveole ThisDrawing, MyFBloc.DefinirEspace(1, 1, CadreY, CadreX, a(0), a(1) - (4 * l), Cercle), acByBlock, _
                    "TOTO :", "toto", "12345678", CadreY, CadreX, MyFBloc, NbL + 1 - Val(l) & "-" & NbC + 1 - Val(c), Cercle
                    
'        A,B,C...
        Case "A"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(i), Cercle
'        A1,A2,A3...
         Case "A1"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(Val(l)) & Val(c), Cercle
                    
'        A10,A9,A8...
        Case "A10"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(Val(l)) & NbL + 1 - Val(c), Cercle
       
'       Z,Y,X...
       Case "Z"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar((NbL * NbC) + 1 - Val(i)), Cercle
'        A-A,A-B,A-C...
        Case "AA"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(Val(l)) & "-" & MyFBloc.CovertNumChar(Val(c)), Cercle
                    
'        A-Z,A-Y,A-X...
        Case "AZ"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(Val(l)) & "-" & MyFBloc.CovertNumChar(NbC + 1 - Val(c)), Cercle
                    
'        Z-A,Z-B,Z-C...
        Case "ZA"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(Val(l)) & "-" & MyFBloc.CovertNumChar(Val(c)), Cercle
                    
'        Z-Z,Z-Y,Z-X...
        Case "ZZ"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(NbL + 1 - Val(l)) & "-" & MyFBloc.CovertNumChar(NbC + 1 - Val(c)), Cercle
       
'        1A,1B,1C...
        Case "1A"
             CreatAlveole ThisDrawing, MyFBloc.DefinirEspace(1, 1, CadreY, CadreX, a(0), a(1) - (4 * l), Cercle), acByBlock, _
                    "TOTO :", "toto", "12345678", CadreY, CadreX, MyFBloc, Val(l) & MyFBloc.CovertNumChar(Val(c)), Cercle
        
'        10A,10B,10C...
        Case "10A"
                   CreatAlveole ThisDrawing, MyFBloc.DefinirEspace(1, 1, CadreY, CadreX, a(0), a(1) - (4 * l), Cercle), acByBlock, _
                    "TOTO :", "toto", "12345678", CadreY, CadreX, MyFBloc, NbL + 1 - Val(l) & MyFBloc.CovertNumChar(Val(c)), Cercle

'        Z1,Z2,Z3...
        Case "Z1"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(NbL + 1 - Val(l)) & Val(c), Cercle
                    
'        Z10,Z9,Z8...
        Case "Z10"
            CreatAlveole ThisDrawing, MyFBloc.DefinirEspace(1, 1, CadreY, CadreX, a(0), a(1) - (4 * l), Cercle), acByBlock, _
                    "TOTO :", "toto", "12345678", CadreY, CadreX, MyFBloc, MyFBloc.CovertNumChar(NbL + 1 - Val(l)) & NbC + 1 - Val(c), Cercle
                    
'        1Z,1Y,1Z...
        Case "1Z"
             CreatAlveole ThisDrawing, MyFBloc.DefinirEspace(1, 1, CadreY, CadreX, a(0), a(1) - (4 * l), Cercle), acByBlock, _
                    "TOTO :", "toto", "12345678", CadreY, CadreX, MyFBloc, Val(l) & MyFBloc.CovertNumChar(NbC + 1 - Val(c)), Cercle
                    
'        10Z,10Y,10X...
        Case "10Z"
             CreatAlveole ThisDrawing, MyFBloc.DefinirEspace(1, 1, CadreY, CadreX, a(0), a(1) - (4 * l), Cercle), acByBlock, _
                    "TOTO :", "toto", "12345678", CadreY, CadreX, MyFBloc, NbL + 1 - Val(l) & MyFBloc.CovertNumChar(NbC + 1 - Val(c)), Cercle
       

       
        Case Else

End Select


    If Cercle = False Then
        a(0) = a(0) + CadreX + 4
     Else
        a(0) = a(0) + CadreY + 4
     End If
    Next
a(1) = a(1) - CadreY - 4
Next
MyPos(0) = 0
MyPos(1) = 0
MyPos(2) = MyPos(2) + 10
MyPos(3) = MyPos(3) + 10 + 15.6908

''MyFBloc.CreateLigne ThisDrawing, XY1, XY2, acByBlock
'XY1(0) = MyPos(0)
'XY1(1) = XY1(1) - 10
'XY2(0) = MyPos(2)
'XY2(1) = XY2(1) - 10
'MyFBloc.CreateLigne ThisDrawing, XY1, XY2, acByBlock
'MyFBloc.CrateCadre ThisDrawing, MyPos, acByBlock
NewConnecteur = MyPos


End Function

Sub CreatAlveole(MyDocumment, InsertPointCadre, Couleur As Long, Prompt As String, txt As String, Defaulttxt As String, CadreY As Double, CadreX As Double, MyFBloc As FunCreateObjet, index As String, Crecle As Boolean)
Dim XY1(0 To 2) As Double
Dim XY2(0 To 2) As Double
Dim InsertCadre(0 To 4) As Double
InsertCadre(0) = InsertPointCadre(0)
InsertCadre(1) = InsertPointCadre(1)
InsertCadre(2) = InsertPointCadre(2)
InsertCadre(3) = InsertPointCadre(3)
InsertCadre(1) = InsertCadre(3) - (CadreY * 1 / 4)
If Crecle = False Then
MyFBloc.CrateCadre MyDocumment, InsertCadre, acByBlock
 
 XY1(0) = InsertCadre(0) + (CadreX / 2)
       XY1(1) = InsertCadre(1) + ((InsertCadre(3) - InsertCadre(1)) * 3 / 2)
       
       MyFBloc.CreateEtiquette MyDocumment, "" & index, XY1, acBlockReference, acAlignmentMiddleCenter
       
       XY1(0) = InsertCadre(0) + (CadreX / 2)
       XY1(1) = InsertCadre(1) + ((InsertCadre(3) - InsertCadre(1)) * 1 / 2)
       MyFBloc.CreateAttribue MyDocumment, "LIASON " & index & " :", "LIAI" & index, "", XY1, acMagenta, acAlignmentMiddleCenter
InsertCadre(3) = InsertCadre(1)
InsertCadre(1) = InsertCadre(3) - (CadreY * 3 / 4)
MyFBloc.CrateCadre MyDocumment, InsertCadre, acByBlock
 XY1(0) = InsertCadre(0) + (CadreX / 2)
       XY1(1) = InsertCadre(1) + ((InsertCadre(3) - InsertCadre(1)) * 1 / 4)
       MyFBloc.CreateAttribue MyDocumment, "FILS " & index & " :", "FILS" & index, "", XY1, acMagenta, acAlignmentMiddleCenter
       XY1(0) = InsertCadre(0) + (CadreX / 2)
       XY1(1) = InsertCadre(1) + ((InsertCadre(3) - InsertCadre(1)) * 3 / 4)
       MyFBloc.CreateAttribue MyDocumment, "MARIAGE " & index & " :", "MAR" & index, "", XY1, acMagenta, acAlignmentMiddleCenter
       
Else
    XY1(0) = InsertCadre(0) + (CadreY / 2)
    XY1(1) = InsertCadre(1) + (CadreY / 2)
    MyFBloc.CrateCercle MyDocumment, XY1, (CadreY / 2), Couleur
    XY1(0) = InsertCadre(0) + (CadreY * 1 / 6)
    XY1(1) = InsertCadre(1) + (CadreY * 4 / 6)
    XY2(0) = XY1(0) + (CadreY * 4 / 6)
    XY2(1) = XY1(1)
    MyFBloc.CreateLigne MyDocumment, XY1, XY2, Couleur
    XY1(0) = InsertCadre(0) + (CadreY / 2)
    XY1(1) = XY1(1) + 3
    MyFBloc.CreateAttribue MyDocumment, "LIASON " & index & " :", "LIAI" & index, "", XY1, acMagenta, acAlignmentMiddleCenter
    XY1(1) = XY1(1) - 6
    MyFBloc.CreateAttribue MyDocumment, "FILS " & index & " :", "FILS" & index, "", XY1, acMagenta, acAlignmentMiddleCenter
    XY1(1) = XY1(1) - 6
    MyFBloc.CreateAttribue MyDocumment, "MARIAGE " & index & " :", "MAR" & index, "", XY1, acMagenta, acAlignmentMiddleCenter
    XY1(1) = XY1(1) + CadreY
    MyFBloc.CreateEtiquette MyDocumment, "" & index, XY1, acBlockReference, acAlignmentMiddleCenter
End If
       ThisDrawing.Application.ZoomAll
       
'MyFBloc.CrateCadre MyDocumment, InsertPointCadre, acMagenta
      
'        XY1(1) = InsertPointCadre(3)
'        XY2(0) = InsertPointCadre(1)
'        XY2(1) = InsertPointCadre(3)
'
'       XY1(1) = (XY1(1) + CadreY) * 3 / 4
'
'         XY2(1) = (XY2(1) + CadreY) * 3 / 4
'         XY2(0) = XY2(0) + CadreX
'        MyFBloc.CreateLigne ThisDrawing, XY1, XY2, acByBlock
'
'        XY1(0) = InsertPointCadre(1)
'        XY1(1) = InsertPointCadre(3)
'        XY2(0) = InsertPointCadre(1)
'        XY2(1) = InsertPointCadre(3)
'         XY1(1) = (XY1(1) + CadreY) * 5 / 4
'
'         XY2(1) = (XY2(1) + CadreY) * 5 / 4
'         XY2(0) = XY2(0) + CadreX
'        MyFBloc.CreateLigne ThisDrawing, XY1, XY2, acByBlock
End Sub

Sub Deparage()
Dim XY1(0 To 2) As Double
Dim XY2(0 To 2) As Double
Dim MyPos
'Choose Select Objects.

Application.Documents("Relai1.dwg").SendCommand " _ai_selall Choix des objets en cours...terminé."

   Application.Documents("Relai1.dwg").SendCommand "_COPYCLIP "
   Application.Documents("ModelBloc.dwg").SendCommand "_pasteclip Spécifiez le point d'insertion: 100,100 "

MyType = "A1"
MyType = "A10"
MyType = "1A"
MyType = "10A"
MyType = "Z1"
MyType = "Z10"
MyType = "1Z"
MyType = "10Z"
MyType = "1"
MyType = "10"
MyType = "A"
MyPos = NewRealai(36, 15.6908, "a", True)
MyPos = NewRealai(36, Val(MyPos(3)), "10", False)
MyPos = NewConnecteur(36, Val(MyPos(3)), "10", False)
MyPos = NewConnecteur(36, Val(MyPos(3)), "z10", True)
XY1(0) = MyPos(0)
XY1(1) = MyPos(3) - 10
XY2(0) = MyPos(2)
XY2(1) = MyPos(3) - 10
XY1(0) = XY1(0) + (XY2(0) / 2)
XY1(1) = XY1(1) + 5
Dim MyFBloc As New FunCreateObjet
MyFBloc.CreateAttribue ThisDrawing, "Ref Connecteur Client :", "RefConnecteurCli", "123454678", XY1, acMagenta, acAlignmentMiddleCenter
XY1(1) = XY1(1) + 10
MyFBloc.CreateAttribue ThisDrawing, "DESIGNATION :", "DESIGNATION", "", XY1, acMagenta, acAlignmentMiddleCenter
End Sub
